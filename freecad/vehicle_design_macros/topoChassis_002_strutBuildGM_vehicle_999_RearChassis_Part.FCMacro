# -*- coding: utf-8 -*-
#***************************************************************************
#*                                                                               *
#*   Copyright (c) 1989- 2024 Abbott Analytical Products   <http://abbottanp.com/>*
#*                                                                               *
#* This program parameterically builds a chassis entity in exo cage in roll-out 
#*     ready state (less defined steering and suspension system) to use for 
#*     prototyping the invisioned Abiriba_RG  GM EV vehicle 
#*     detailed at: https://abbottanp.com/artifacts/gm_vehicle_WB/index.html.
#*Helpful Sites:
#*  Topographical scripting https://wiki.freecad.org/Topological_data_scripting
#*	Fuse/Union of Selected components
#*	  https://forum.freecad.org/viewtopic.php?t=4137 Re: Fuse multiple parts in 
#*		python macro fails Post by wmayer » Mon Jun 10, 2013 with AAP adjustments
#*	Part Rotation:  Re: how to rotate an object (placement) by yorik 02/06/2012  
#*		https://forum.freecad.org/viewtopic.php?style=5&t=2213
#*		Alternately used LES_Tower style rotation used in topoChassisFrame.py line 204
#*		as seen Ln 204 	#circle.rotate(App.Vector(0, 0, 0),App.Vector(0, 0, 1), 90)
#*		and modified for FrontChassis rotate of 7.5 degrees about X-axis not Z-Axis
#*
#* Change History
"""
#* 250123_lu Results perfect through testing of the frontChassisSection()
#			Test for the topoChassisToolbox usage of SF in the seting of lenght
#			diameter, and radius.

250121_lu Successfully built Chassis Rear Frame assembly using aap_lib.
			topoChassisToolbox.RearChassisSection() for 000_987_spike_aapLib_test4Rear.FCStd
			resulting in orineted rear shape afft-RR to Front and bow-MID to Rear.
			See 000_979_spike_assembleStruts4RearChassis driven by 
			topoChassis_005_assembleGM_vehicle999_rearChassis_subAssy.FCMacro

250121_lu testing the introduciton of topoChassisToolbox.py and the aap_lib module

241018_lu restart effort
"""
#* 240921_tr topoChassis_mainBuildGM_vehicle_002_RearChassis.FCMacro spun from 
#*				topoChassis_mainBuildGM_vehicle_001_FrntChassis.FCMacro.  Used gloabl
#*				replacement for MID->Bow, RR->Aft, and Rear->Frnt
#*
#**	Tricks of Trade:
#** 1> After un-commenting the Begin Op --- End Op content check to insure the the message
#***		'End of Active Development' and carriageretrun/newline symbol are teh only other 
#***		content visible.  Everything else should be grayed-out or commneted-out.  EXCEPT
#***		FOR the content at the def section and declarations immediately above the def's
#*** Things That Go Bump In The Night:
#***		1> 




#uncomment for usage:
from topoChassisFrame import rearChassisSection
#uncomment for usage:
#from topoChassisCabin import cabinChassisSection
import FreeCAD as App
import aap_lib


__title__="Fuse the Rear Chassis Struts into A Part With A Macro"
__author__ = "Lucca Uzzo"
__url__ = "http://abbottanp.com"

# begin abstract from aapLib_fire1.FCMacro
from aap_lib import aapfunctions, topoChassisToolbox

chassisTool_Error = 0
chassisListVar_Error = 0
chassisShapeOpn_Error = 0

try:
	wrktool = topoChassisToolbox.chassisTool()
except Exception:
	print("chassisTool issue.  wrktool can not be defined")
	chassisTool_Error = 9
try:
    wrkdata = topoChassisToolbox.chassisListVar()
except Exception:
    print("chassisListVar issue.  wrkdata can not be defined")
    chassisListVar_Error = 9
try:
    wrkShape= topoChassisToolbox.chassisShapeOpn()
except Exception:
    print("chassisShapeOpn issue.  wrkdata can not be defined")
    chassisShapeOpn_Error = 9

#testing for trigger
### STEP 1: create, save, close, then invoke/activate new project file
#250121_lu  wrkPrjFile = "_00_979_spike_assembleStruts4RearChassis"
wrkPrjFile = "_00_987_spike_aapLib_test4Rear"  
wrkShapeObj   = 'Shape'      #Let FreeCAD do the naminging work during building

App.setActiveDocument(wrkPrjFile)
App.ActiveDocument=App.getDocument(wrkPrjFile)
Gui.ActiveDocument=Gui.getDocument(wrkPrjFile)


def getStri(startNdx):
		if startNdx < 10 :
			stri = '00' + str(startNdx)
		else:
			stri = '0' + str(startNdx)
		return stri

def removeShape(wrkShapeTarget):
	### Begin command Std_Delete
	App.getDocument(wrkPrjFile).removeObject(wrkShapeTarget)
	App.getDocument(wrkPrjFile).recompute()
	### End command Std_Delete

def rtnSelection(startNdx, endNdx):
	Gui.Selection.clearSelection()
	if startNdx == 0:  #  if first item in list use the default Shape label
		Gui.Selection.addSelection(wrkPrjFile,wrkShapeObj)
		App.Console.PrintMessage('startNdx 0')
		App.Console.PrintMessage('\n')
	else:  #if starting at some other place in the list reset Shape??? naming
		stri = getStri(startNdx)
		wrkShapeLabel = wrkShapeObj+stri
		Gui.Selection.addSelection(wrkPrjFile,wrkShapeLabel)
		# dev App.Console.PrintMessage('startNdx > 0')
		# dev App.Console.PrintMessage('\n')

	# dev App.Console.PrintMessage(wrkShapeLabel)
	# dev App.Console.PrintMessage('\n')
	startNdx += 1	# assumes the first item is skipable but needed in selection
	while startNdx < endNdx + 1:	# first item named Shape 2nd Shape001
		wrkShapeLabel = 'Nope'
		#dev 
		App.Console.PrintMessage(startNdx)
		#dev 
		App.Console.PrintMessage('\n')
		stri = getStri(startNdx)
		wrkShapeLabel = wrkShapeObj+stri 
		Gui.Selection.addSelection(wrkPrjFile,wrkShapeLabel)
		if (wrkShapeLabel != 'Shape004'): # or (wrkShapeLabel != 'Shape009'):   #Assumes droppabble polygons non-tube paths
			App.Console.PrintMessage(wrkShapeLabel)
			App.Console.PrintMessage('\n')
		startNdx += 1
	return 	Gui.Selection.getSelection()	#selectItems = 



# Create the basic front chassis  


### STEP 2: Create Shape...Shape013 using uncomment below then Comment-out
# Create the basic rear chassis  
"""
"""
#$$$ Begin Op
App.Console.PrintMessage("Comment/UnComment as Needed\n")
rearChassisSection()
#$$$ End Op
"""
"""
### STEP 3: create Rear Chassis MID Section by 
###			1> Uncommenting for veiwable between "#$$$ Begin Op" 
###				to "#$$$ End Op" for STEP 3:
###			2> Uncomment removeShape() in two places to delete Shape 4 and Shape9 
###			3> Run Macro again
###			4> Verifiy results
###				4.1> Shape..Shape008 selected (highlighted)
###				4.2>	 New Object: Label shown in Model Tree: FusedRearMID_Chassis_
###				Note: All content below this STEP should be no-op or information print of 
###				message:  'End of Active Development'
###			5> Comment-out this step and move to STEP 4.
###				Note: Insure the two removeShap() entries are commented-out 


"""
#$$$ Begin Op
#Prepare to fuse bow and aft sections of Front Chassis
# Once the "tubes" for the front chassis have been create 
#	fuse them into a Part called: FusedRearMID_Chassis

App.Console.PrintMessage("Comment/UnComment as Needed\n")
App.Console.PrintMessage("Select shapes in the Front Chassis MID section\n")
wrkShapeTarget= 'Shape004'    #front chassis bow polygon
#comment-out for dev removeShape(wrkShapeTarget)
wrkShapeTarget= 'Shape009'    #front chassis aft polygon
#comment-out for dev  removeShape(wrkShapeTarget)

#post removal of unwanted Labeled objects like polygon used for development
startNdx = 0		# First Labeled item/tube/shape of chassis
endNdx   = 8		# Last Labeled item/tube/shape of chassis	 

selectItems = rtnSelection(startNdx, endNdx)
newShape = selectItems[0].Shape
App.Console.PrintMessage(selectItems[0].Shape)
App.Console.PrintMessage('\n')

i = 1 # skip first selected shape
while i < endNdx:   # no longer worry about Shape 4
	newShape = newShape.fuse(selectItems[i].Shape)
	App.Console.PrintMessage(selectItems[i].Shape)
	App.Console.PrintMessage('\n')
	i += 1
newObject = App.ActiveDocument.addObject("Part::Feature","FusedRearMID_Chassis\n")
newObject.Shape = newShape
App.ActiveDocument.recompute()
#$$$ End op
"""


### STEP 4: create Front Chassis RR Section by 
###			1> Uncommenting for veiwable content between "#$$$ Begin Op" 
###				to "#$$$ End Op" for STEP 3:
###			2> Run Macro again
###			3> Verifiy results
###				3.1> Shape10..Shape013 selected (highlighted)
###				3.2>	 New Object: Label shown in Model Tree: FusedRearRR_Chassis_
###			Note: All content below this STEP should be no-op or information print of 
###			message:  'End of Active Development'



# Once the "tubes/struts" for the rear chassis have been create 
#	fuse them into a Part called: FusedRearRR_Chassis
"""


### Begin Op
startNdx = 10		# First Labeled item/tube/shape of chassis
endNdx   = 13		# Last Labeled item/tube/shape of chassis	 
selectItems = rtnSelection(startNdx, endNdx)
newShape = selectItems[0].Shape  # new set of items 0-4
App.Console.PrintMessage(selectItems[0].Shape)
App.Console.PrintMessage('\n')
i = 1 # skip first selected shape
while i < 4:   # no longer worry about Shape 4
	newShape = newShape.fuse(selectItems[i].Shape)
	App.Console.PrintMessage(selectItems[i].Shape)
	App.Console.PrintMessage('\n')
	i += 1
newObject = App.ActiveDocument.addObject("Part::Feature","FusedRearRR_Chassis\n")
newObject.Shape = newShape
App.ActiveDocument.recompute()
### End Op
"""


### STEP 5: create Rear Chassis MID Section by 
###			1> Uncommenting for veiwable content between "#$$$ Begin Op" to 
###				"#$$$ End Op" for STEP 5:
###			2> Run Macro again
###			3> Verifiy results
###				3.1> FusedFntMID_Chassis and FusedRR_Chassis selected (highlighted)
###				3.2>	 New Object: Label shown in Model Tree: FusedRear_Chassis_
###			Note: All content below this STEP should be no-op or information print of 
###			message:  'End of Active Development'


#Fuse: FusedRearMID_Chassis and FusedRearRR_Chassis
#Rotate about X-axis 7.5 degrees

"""
#$$$ Begin Op
App.Console.PrintMessage("Comment/UnComment as Needed\n")
App.Console.PrintMessage("Select fused solids\n")
App.Console.PrintMessage("	FusedRearMID_Chassis\n")
App.Console.PrintMessage("	FusedRearRR_Chassis\n")
Gui.Selection.clearSelection()
Gui.Selection.addSelection(wrkPrjFile,'FusedRearMID_Chassis_')
Gui.Selection.addSelection(wrkPrjFile,'FusedRearRR_Chassis_')
# using GUI selection from python console 
selectItems = Gui.Selection.getSelection()
newShape = selectItems[0].Shape  # new set of items 0-4
App.Console.PrintMessage(selectItems[0].Shape)
App.Console.PrintMessage('\n')
App.Console.PrintMessage(newShape)
App.Console.PrintMessage('\n')
i = 1 # skip first selected shape
while i < 2 :
	newShape = newShape.fuse(selectItems[i].Shape)
	App.Console.PrintMessage(selectItems[i].Shape)
	App.Console.PrintMessage('\n')
	i += 1

newObject = App.ActiveDocument.addObject("Part::Feature","FusedRear_Chassis\n")
newObject.Shape = newShape
App.ActiveDocument.recompute()
#$$$ End Op
"""


### STEP 6: create Front Chassis MID Section by 
###			1> Uncommenting for veiwable content between "#$$$ Begin Op" to 
###				"#$$$ End Op" for STEP 6:
###			2> Change hardcoded Object Labels as needed to reflect any user defined names.
###			3> Run Macro again
###			4> Verifiy results
###				4.1> BodyRearChassisClone created
###				4.2>	 CloneRearChassis is available in Model Tree_
###			Note: All content below this STEP should be no-op or information print of 
###			message:  'End of Active Development'

# Create a Clone for the Front Chassis
### Begin command PartDesign_CloneRearChassis

"""
#$$$ Begin Op
App.getDocument( wrkPrjFile ).addObject('PartDesign::Body','BodyRearChassisClone_')
App.getDocument( wrkPrjFile ).addObject('PartDesign::FeatureBase','CloneRearChassis')
App.getDocument( wrkPrjFile ).getObject('BodyRearChassisClone_').Group = [App.getDocument( wrkPrjFile ).getObject('CloneRearChassis')]
App.getDocument( wrkPrjFile ).getObject('BodyRearChassisClone_').Tip = App.getDocument( wrkPrjFile ).getObject('CloneRearChassis')
App.getDocument( wrkPrjFile ).getObject('CloneRearChassis').BaseFeature = App.getDocument( wrkPrjFile ).getObject('FusedRear_Chassis_')
App.getDocument( wrkPrjFile ).getObject('CloneRearChassis').Placement = App.getDocument( wrkPrjFile ).getObject('FusedRear_Chassis_').Placement
App.getDocument( wrkPrjFile ).getObject('CloneRearChassis').setEditorMode('Placement', 0)
App.ActiveDocument.recompute()
App.getDocument( wrkPrjFile ).getObject('CloneRearChassis').ViewObject.ShapeColor=getattr(App.getDocument( wrkPrjFile ).getObject('FusedRear_Chassis_').getLinkedObject(True).ViewObject,'ShapeColor',App.getDocument( wrkPrjFile ).getObject('CloneRearChassis').ViewObject.ShapeColor)
App.getDocument( wrkPrjFile ).getObject('CloneRearChassis').ViewObject.LineColor=getattr(App.getDocument( wrkPrjFile ).getObject('FusedRear_Chassis_').getLinkedObject(True).ViewObject,'LineColor',App.getDocument( wrkPrjFile ).getObject('CloneRearChassis').ViewObject.LineColor)
App.getDocument( wrkPrjFile ).getObject('CloneRearChassis').ViewObject.PointColor=getattr(App.getDocument( wrkPrjFile ).getObject('FusedRear_Chassis_').getLinkedObject(True).ViewObject,'PointColor',App.getDocument( wrkPrjFile ).getObject('CloneRearChassis').ViewObject.PointColor)
App.getDocument( wrkPrjFile ).getObject('CloneRearChassis').ViewObject.Transparency=getattr(App.getDocument( wrkPrjFile ).getObject('FusedRear_Chassis_').getLinkedObject(True).ViewObject,'Transparency',App.getDocument( wrkPrjFile ).getObject('CloneRearChassis').ViewObject.Transparency)
App.getDocument( wrkPrjFile ).getObject('CloneRearChassis').ViewObject.DisplayMode=getattr(App.getDocument( wrkPrjFile ).getObject('FusedRear_Chassis_').getLinkedObject(True).ViewObject,'DisplayMode',App.getDocument( wrkPrjFile ).getObject('CloneRearChassis').ViewObject.DisplayMode)
App.ActiveDocument.recompute()
### End command PartDesign_Clone
#$$$ End Op
"""


App.Console.PrintMessage('End of Active Development') 
App.Console.PrintMessage('\n')
