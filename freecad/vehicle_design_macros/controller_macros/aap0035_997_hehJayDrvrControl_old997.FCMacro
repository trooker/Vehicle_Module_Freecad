# -*- coding: utf-8 -*-
#***************************************************************************
#*                                                                               *
#*   Copyright (c) 1989- 2025 Abbott Analytical Products   <http://abbottanp.com/>*
#*                                                                               *
#* This program is a spike for bringing simple QtDesign layout into the FreeCAD - Abbott
#*    prototyping the invisioned Abiriba_RG  GM EV vehicle 
#*    detailed at: https://abbottanp.com/artifacts/gm_vehicle_WB/index.html.
#*Helpful Sites:
'''
250421_lu Incorporate lessons from aap0035_003_002_compass.FCMacro into aapNavDial
        Grub: PySide2 QDial needle draw/paint
        AI: https://www.google.com/search?client=ubuntu-sn&channel=fs&q=PySide2+QDial+needle+draw%2Fpaint


250419_lu Introduce operational performance simulation:
        Assumptions: Flat, Hard Dirt, Aerodynamic = 0 until 55mph Coff of Friction Force = mu * N
                       See Holy Grail of AWD System Rivian R1T video of article 4.56 and 6.56 for discussion for mu
                       https://insideevs.com/news/593277/engineering-explained-talks-rivian-r1t-holy-grail-awd-systems/
        Variables considered 
            Service Weight: Vehicle estimate, crew of two, combat load for three days.
            Surface: Dry Hard, see Rivian study
            Slope: Flat, Slopes Up, Slopes Down
            Vehicle KWH/MPH Pre Aerodynamic 0-55 mph
            Vehicle KWH/MPH Post Aerodynamic 55 to 75 mph
        Integration and unit testing completed

250418_lu Begin integrate aap0035_hehJayDrvrControl_999.FCMacro with the aap0035_997_customSignal4Dial.FCMacro
        dial behavior.


250415_lu (abstracted from aap0035_0097customSignal4Dial)
       Works well with mouse and numpad
       With Left mouse 
       start:: run app/macro
       reset:: move mouse out of dial area

              port::                  starboard::
       step moves
              left (port pad)         right (port pad)   NOTE: right pad used for accelerator
              left arrow              right arrow
              4/2 numpad              6/8 numpad
              mouse roller            mouse roller
       rapid jumps
              page down               page up
              pg dn                   pg up
       position jumps
              port: minimum           starboard: maximum      
              home


250412_lu Continue journey.
        Grub: PySide2 for a dialog form with a QWidget object that inherets from QDial what custom signals are required to signal the event of a mouse entering the dial so that a connection can be made to a Form's function 
        https://www.google.com/search?client=ubuntu-sn&channel=fs&q=PySide2+for+a+dialog+form+with+a+QWidget+object+that+inherets+from+QDial+what+custom+signals+are+required+to+signal+the+event+of+a+mouse+entering+the+dial+so+that+a+connection+can+be+made+to+a+Form%27s+function+
        Grub: PySide2 example using widget that inherets QDial but uses custom signals to connect to slots in a dialog form.
        AI gave close model that worked.  But.. did not treanslate to target aap0035_...
        https://www.google.com/search?client=ubuntu-sn&channel=fs&q=PySide2+example+using+widget+that+inherets+QDial+but+uses+custom+signals+to+connect+to+slots+in+a+++++++++++dialog+form.

250411_lu Implemented leaveEvent handling usig by building aapLib aapDial class
        Grub: PySide2 what are the supported types for custom signal connect     self.dialUI.mouseEnters.connect(self.dialActive) <class 'TypeError'>: 'PySide2.QtCore.QObject.connect' called with wrong argument types:   PySide2.QtCore.QObject.connect(aapDial, str, bool) Supported signatures:
        https://wiki.qt.io/Qt_for_Python_Signals_and_Slots
        Grub: Freecad Python QWidget.QDial leaveEvent() AI example as guide
        https://www.google.com/search?client=ubuntu-sn&channel=fs&q=Freecad+Python+QWidget.QDial+leaveEvent%28%29
        Grub: Freecad PySide2 QWidget.QDial leaveEvent()
        https://www.google.com/search?q=Freecad+PySide2+QWidget.QDial+leaveEvent%28%29&client=ubuntu-sn&hs=dqi&sca_esv=0312fbabf4daa587&channel=fs&sxsrf=AHTn8zpAEhiUi8UK_xhOhCAU6DyolWR0PQ%3A1744397407552&ei=X2T5Z8G4IbOhiLMPxqLNyAY&ved=0ahUKEwiB5Mve0tCMAxWzEGIAHUZRE2kQ4dUDCBA&uact=5&oq=Freecad+PySide2+QWidget.QDial+leaveEvent%28%29&gs_lp=Egxnd3Mtd2l6LXNlcnAiKkZyZWVjYWQgUHlTaWRlMiBRV2lkZ2V0LlFEaWFsIGxlYXZlRXZlbnQoKTIFECEYoAEyBRAhGKABMgUQIRigATIFECEYoAFIoZ0sUJmSKVj9rClwAngAkAEAmAFqoAGUB6oBAzguMrgBA8gBAPgBAZgCDKAC5wfCAgsQABiABBiwAxiiBMICCBAAGLADGO8FwgIIEAAYgAQYogTCAgUQABjvBcICBxAjGLACGCfCAggQIRigARjDBJgDAIgGAZAGBZIHAzguNKAHmyGyBwM2LjS4B9kH&sclient=gws-wiz-serp
        Grub: PySide2QWidget.QDial leaveEvent() document emit signal
        https://www.google.com/search?q=PySide2QWidget.QDial+leaveEvent%28%29+document+emit+signal&client=ubuntu-sn&sca_esv=cdd70d77cbc6b9e0&channel=fs&sxsrf=AHTn8zr3bc3mTqZWfLN-qXQ-CyS1kptslA%3A1744403673833&ei=2Xz5Z9-3MpnQ5NoP7LjwwQk&ved=0ahUKEwifiMuK6tCMAxUZKFkFHWwcPJgQ4dUDCBA&uact=5&oq=PySide2QWidget.QDial+leaveEvent%28%29+document+emit+signal&gs_lp=Egxnd3Mtd2l6LXNlcnAiNlB5U2lkZTJRV2lkZ2V0LlFEaWFsIGxlYXZlRXZlbnQoKSBkb2N1bWVudCBlbWl0IHNpZ25hbDIHECEYoAEYCjIHECEYoAEYCjIFECEYqwIyBRAhGKsCMgUQIRirAkjxQlCcAljUJ3ABeAGQAQCYAagBoAGyDKoBBDAuMTK4AQPIAQD4AQGYAg2gAqoNwgIKEAAYsAMY1gQYR5gDAIgGAZAGCJIHBDEuMTKgB_JUsgcEMC4xMrgHmw0&sclient=gws-wiz-serp
250330_lu Issue with Slider
python  QSlider value change
https://stackoverflow.com/questions/43152489/pyqt5-qslider-valuechanged-event-with-delay

'''

import sys
from PySide2 import QtWidgets, QtCore
from PySide2.QtWidgets import (QApplication, QWidget, QPushButton, QDial, QSlider, QVBoxLayout, QHBoxLayout, QLabel)
from PySide2 import QtGui, QtCore
from PySide2.QtGui import QFont, QColor
from PySide2.QtCore import (Qt, Slot, QTimer)
from PySide2.QtCore import Signal, QEvent
from PySide2.QtGui import QCursor

#For later implementation
#from aapLib import aapNavDial


class aapNavDial(QDial):   #was QtWidgets.QDial):
    valueChangedCustom = QtCore.Signal(int)
    mouseHovers = QtCore.Signal(int)
    mouseEnters = QtCore.Signal(int)  #aap Signal
    mouseExits  = QtCore.Signal(int)  #aap Signal
 

    def __init__(self, parent=None):
        super().__init__(parent)
        self.setMinimum(0)
        self.setMaximum(100)
        self.dialCenter = 50
        self.setGeometry(50, 50, 150, 150)
        self.setValue(self.dialCenter) # Initial value
        self.setNotchesVisible(True)
        self.last_value = self.dialCenter
        self.valueChanged.connect(self._emit_custom_signal)
        self.mouseHovers.connect(self.hoverEvent)
        self.mouseEnters.connect(self.enterEvent)
        self.mouseExits.connect(self.leaveEvent)
        App.Console.PrintMessage('begin aap0035_003_002\n')       
    ## begin from aap0035_003_002
        self.setMinimumSize(200, 200)
    """   """
    def paintEvent(self, event):
        #Makes it worst 
        super(appNavDial, self).paintEvent(event)

        App.Console.PrintMessage('paintEvent\n')       
        painter = QPainter(self)
        #painter.begin(self.aapNavDial())
        painter.begin(self.viewport())
        painter.setRenderHint(QPainter.Antialiasing)

        # Background circle
        painter.setBrush(QColor(50, 50, 50))
        painter.drawEllipse(self.rect().center(), min(self.width(), self.height()) // 2 - 2, min(self.width(), self.height()) // 2 - 2)

        # Needle
        painter.setBrush(QColor(255, 0, 0))
        angle = self.value() / (self.maximum() - self.minimum()) * 360  # Calculate angle
        center = self.rect().center()

        # Needle polygon
        needle_length = min(self.width(), self.height()) // 2 - 10
        p1 = QPoint(center.x(), center.y() - needle_length)
        p2 = QPoint(center.x() + 5, center.y()+30)
        p3 = QPoint(center.x() - 5, center.y()+30)

        # Needle Knob
        polygon = QPolygon([p1, p2, p3])
        painter.translate(center)
        painter.rotate(angle)
        painter.translate(-center)
        painter.drawConvexPolygon(polygon)
        #painter.drawEllipse(self.rect().center(), 25, 25)
        painter.drawEllipse(center.x()-12.5,center.y()+20, 25, 25)


        # Center circle
        painter.setBrush(QColor(255, 255, 255))
        painter.drawEllipse(self.rect().center(), 5, 5)
        """   """
        App.Console.PrintMessage('end aap0035_003_002\n')       
   
   ## end from aap0035_003_002
        painter.end()

    def _emit_custom_signal(self, value):
        #print('value change')
        self.valueChangedCustom.emit(value)

    def hoverEvent(self,event):
        #print("Mouse hovering over dial")
        self.setValue(self.last_value)
        self.mouseHovers.emit(9999)
        self.on_value_changed(9999)
        self._emit_custom_signal(9999)
        self.isDialHot = True       

    def enterEvent(self, event):
         # Code to execute when the mouse leaves the dial
        #print("Mouse entered the dial")
        self.setValue(self.last_value)
        self.mouseEnters.emit(1111)
        self.on_value_changed(1111)
        self._emit_custom_signal(1111)
        self.isDialHot = True        


    def leaveEvent(self, event):
         # Code to execute when the mouse leaves the dial
        #print("Mouse left the dial")
        self.setValue(self.last_value)
        self.isDialHot = False
        self.mouseExits.emit(1001)
        self.on_value_changed(1001)
        self._emit_custom_signal(1001)

    def on_value_changed(self, value):
        self.last_value = value
        '''
        for __init()__
        add         self.dialUI.valueChanged.connect(self.update_steerLabel)
        '''
        


def create_btnEStop(steerLabel, callback):
    button = QPushButton(steerLabel)
    button.clicked.connect(callback)
    button.setStyleSheet("background-color: red;")
    #button.setStyleSheet("font-color: white;")
    button.setGeometry(50, 50, 150, 150)
    # Font and size
    font = QFont("Arial", 34)
    button.setFont(font)
    # Color
    button.setStyleSheet("QPushButton {color: white; background-color: red;}")
    #button.setVisible(False)
    return button



def create_button(steerLabel, callback):
    button = QPushButton(steerLabel)
    button.clicked.connect(callback)
    return button

"""
Hold for future possible use
def create_dial(min_val, max_val, center_val, callback):
    App.Console.PrintMessage('create aapNavDial\n')       
    dial = aapNavDial()
    dial.setMinimum(min_val)
    dial.setMaximum(max_val)
    dial.setValue(center_val)
    dial.setNotchesVisible(True)
    dial.lastvalue = center_val
    dial.valueChanged.connect(callback)
    dial.setTracking(True)   #insure value changes with corsor move
    #dial.setVisible(False)
    App.Console.PrintMessage('Returning to home plate\n')
    return dial
"""

def create_Accel_Slider(min_val,max_val ,tickpos,callback):
 #   slider = QSlider(min_val, max_val, tickpos)
    slider = QSlider()
    slider.setMinimum(min_val)
    slider.setMaximum(max_val)
    slider.setValue = 0
    slider.TickPosition = 3
    slider.valueChanged.connect(callback)
    #slider.setVisible(False)
    return slider

def create_Fuel_Slider(min_val, max_val,callback):
    slider = QSlider()
    slider.setMinimum(0)
    slider.setMaximum(100)
    slider.TickPosition = 3
    slider.setValue(100)
    slider.valueChanged.connect(callback)
    #slider.setVisible(False)
    return slider




class Foo(QWidget):
    def __init__(self, parent=None):
        super(Foo,self).__init__(parent)
        self.isRunning = False
        self.started = False    #starter button requires a push
        self.hasEStopBnPushed = False
        self.objActive = 1
        self.objReleased = 0
        self.timer_id = -1
        self.setWindowTitle("Foobar Tracker")
        self.setGeometry(200, 200, 520, 520)
        self.steerLabel = QLabel("Click Start Stop to Activate/Halt")
        self.btnStarter = create_button("Start", self.on_button_clicked)
        self.btnEStop   = create_btnEStop("Emergemcy\n Stop", self.on_button_clicked)
        self.btnEStop.clicked.connect(self.btnEStop_toggle_visibility)
        EStoplayout = QHBoxLayout()
        EStoplayout.addStretch()  # Add stretch to push the button to the right
        EStoplayout.addWidget(self.btnEStop, alignment=Qt.AlignRight | Qt.AlignBottom)
        self.dialMin = 0
        self.dialMax = 100
        self.dialCenter = 50
        self.dialLastValue =  self.dialCenter
        self.dialActive = False  #dialUI is not active yet.  Mouse needs to hoover over
        #self.dialUI = create_dial(self.dialMin, self.dialMax, self.dialCenter, self.on_dial_changed)
        #self.dialUI.mouseHovers.connect(self.dialHovers)
        #self.dialUI.mouseEnters.connect(self.dialActive)
        #self.dialUI.mouseExits.connect(self.dialReleased,self.objReleased)
        #move ln 266 to end of new def for dial
        # begin dial aap0035_997 
        self.isDialHot = False 
        #Flags used ot turn messages on/off and control redundant messages
        self.FlipFlagExit = True   #Begins as True: just exited
        self.FlipFlagEnter = False
        self.dialUI = aapNavDial()
        self.dialUI.valueChangedCustom.connect(self.update_label)
        self.dialUI.valueChanged.connect(self.update_label)
        self.dialUI.mouseHovers.connect(self.dialHovers(9999))
        #self.dialUI.mouseEnters.connect(self.dialActive(1111))
        self.dialUI.mouseExits.connect(self.dialReleased(1001))
        self.dialUI.valueChanged.connect(self.on_dial_changed)
        self.dialUI.setFocusPolicy(Qt.FocusPolicy.StrongFocus) # Allow dial to receive focus
        App.Console.PrintMessage('self.dialUI should be available\n')       
        self.update_label(-1)
        self.steerHoldValue = self.dialUI.value()  #old ln 266
        
        # end dial aap0035-997
        #dashBoradLayout = QHBoxLayout()
        self.sliderAccel = create_Accel_Slider(0,100,3, self.on_sliderAccel_valueChanged)
        self.sliderFuel =  create_Fuel_Slider(0,100, self.on_sliderFuel_valueChanged)
        #dashBoradLayout.addWidget(self.sliderAccel)
        #dashBoradLayout.addWidget(self.btnEStop)

        wndlayout = QVBoxLayout()
        wndlayout.addWidget(self.btnStarter)
        wndlayout.addWidget(self.steerLabel)
        wndlayout.addWidget(self.dialUI)
        wndlayout.addWidget(self.sliderAccel)
        wndlayout.addWidget(self.sliderFuel)
        wndlayout.addWidget(self.btnEStop)
        #wndlayout.addWidget(dashBoradLayout)
        self.setLayout(wndlayout)
 
    """
    lost direction on this one
    def timerEvent(self, event):
        self.killTimer(self.timer_id)
        self.timer_id = -1
        heavy_task()

    def value_changed(self):
        if self.timer_id != -1:
            self.killTimer(self.timer_id)

        self.timer_id = self.startTimer(3000)
    """    
    ##  begin from aap0035_997
    def set_dial_value(self, value):
         self.dial.setValue(value)

    def on_dial_changed(self, value):
        #Reset to 50 when focus changes
        if value != 50:
            self.dial.setValue(50)


    @Slot()
    def update_label(self, value):
        if value == 1001:  #Mouse exits  Dial
            # dev print('Cursor not in Dial')
            if self.FlipFlagExit == False:
                 # dev print("isDialHot Flipping to False")
                 self.FlipFlagExit = True
                 self.FlipFlagEnter = False
            self.steerLabel.setText(f"Value: {'Forward'}")
            # dev self.steerLabel.setText(f"Value: {'Forward Now Going Cold 1001'}")
            self.dialUI.setValue(self.dialCenter)
            if self.isDialHot == True:
                self.last_value = self.dialCenter
                self.isDialHot = False
                #self.dialUI.setCursor(QCursor(Qt.ArrowCursor))
        elif value == 1111: #Mouse enters Dial setup for fresh turn
            # dev print('Mouse entered dial')
            if self.FlipFlagEnter  == False:
                # devprint("isDialHot Flipping to True")
                self.FlipFlagEnter = True
                self.FlipFlagExit = False
            self.steerLabel.setText(f"Value: {'Forward'}")
            # dev self.steerLabel.setText(f"Value: {'Forward Going Hot '}")
            self.dialUI.setValue(self.dialCenter)
            self.last_value = self.dialCenter
            self.isDialHot = True
            self.dialUI.setCursor(QCursor(Qt.PointingHandCursor))
        elif value == -1:
            # dev print("Welcome.  We are idling")
            self.steerLabel.setText(f"Value: {'Ready'}")
            # dev self.steerLabel.setText(f"Value: {'Waiting for Good-To-Go'}")
            self.dialUI.setValue(self.dialCenter)
            self.last_value = self.dialCenter
            self.isDialHot = False
            self.FlipFlagExit = True
            self.FlipFlagEnter = False
	        
        else: 
            if self.isDialHot == True:
                # dev print('isDialHot is True')
                self.steerLabel.setText(f"Value: {value}")
                self.last_value = value
            """
             else:
                self.dialUI.setValue(self.dialCenter)
                self.last_value = self.dialCenter
           """
 
    @Slot(int)
    #@Slot()
    def dialHovers(self,tstValue):
        #self.dialUI.sliderReleased()
        #App.Console.PrintMessage('Hover over Dial\n')
        print('Hover over Dial\n')
        #self.steerLabel.setText("Forward")
        self.update_label(tstValue)
        self.dialLastValue = self.dialCenter

 
    @Slot(int)
    #@Slot()
    def dialActive(self,tstValue):
        #self.dialUI.sliderReleased()
        #App.Console.PrintMessage('Dial Now  Active\n')
        print('Dial Now Active\n')
        self.update_label(tstValue)
        self.steerLabel.setText("Forward")
        self.dialLastValue = self.dialCenter

    @Slot(int)
    #@Slot()
    def dialReleased(self,tstValue):
        #self.dialUI.sliderReleased()
        #App.Console.PrintMessage('Dial Released\n')
        print('Dial Now Released\n')
        self.steerLabel.setText("Forward")
        self.update_label(tstValue)
        self.dialLastValue = self.dialCenter

               
        ##  end from aap0035_997
    
    """
    @Slot(int)
    #@Slot()
    def dialHovers(self,tstValue):
        #self.dialUI.sliderReleased()
        #App.Console.PrintMessage('Hover over Dial\n')
        print('Hover over Dial\n')
        #self.steerLabel.setText("Forward")
        self.update_label(tstValue)
        self.dialLastValue = self.dialCenter

 
    @Slot(int)
    #@Slot()
    def dialActive(self,tstValue):
        #self.dialUI.sliderReleased()
        #App.Console.PrintMessage('Dial Now  Active\n')
        print('Dial Now Active\n')
        self.update_label(tstValue)
        self.steerLabel.setText("Forward")
        self.dialLastValue = self.dialCenter

    @Slot(int)
    #@Slot()
    def dialReleased(self,tstValue):
        #self.dialUI.sliderReleased()
        #App.Console.PrintMessage('Dial Released\n')
        print('Dial Now Released\n')
        self.steerLabel.setText("Forward")
        self.update_label(tstValue)
        self.dialLastValue = self.dialCenter


    @Slot(int)
    def dialHovers(self):
        #self.dialUI.sliderReleased()
        App.Console.PrintMessage('Dial Active')
        self.steerLabel.setText("Forward")
        self.dialLastValue = self.dialCenter

 
    Slot(int)
    def dialActive(self,tstValue):
        #self.dialUI.sliderReleased()
        App.Console.PrintMessage('Dial Active')
        self.steerLabel.setText("Forward")
        self.dialLastValue = self.dialCenter

    @Slot(int)
    def dialReleased(self,tstValue):
        #self.dialUI.sliderReleased()
        App.Console.PrintMessage('Dial Released')
        self.steerLabel.setText("Forward")
        self.dialLastValue = self.dialCenter
    """


    @Slot()
    def on_sliderAccel_valueChanged(self, value):
        #print('anything!!!\n')
        #if dialReleased() == True:
        print('Speed: ' + str(value)+ ' kph\n')

    @Slot()
    def on_sliderFuel_valueChanged(self, value):
        #print('anything!!!\n')
        #dialReleased()
        print('Speed: ' + str(value)+ ' kwh remaining\n')



    @Slot()
    def update(self):
        #dialReleased()
        self.steerHoldValue = self.dialUI.self.dial.value()
        #App.Console.PrintMessage
        print('Update::   ' + str(self.steerHoldValue) +'\n')


    @Slot()
    def on_button_clicked(self):
        """
        logic needs work 
        """
        #dialReleased()
        if self.isRunning == True:
            self.btnStarter.setText('Stop') 
            self.started = True
        else:
            if self.hasEStopBnPushed == False:
                self.btnStarter.setText('Start') 
                self.started = False 
        if self.hasEStopBnPushed == False:
            print('hasEStopBnPushed == False\n')
            if self.isRunning == True:             
                #App.Console.PrintMessage
                self.btnStarter.setText('Starter') #need to switch button text 
                self.btnEStop_toggle_visibility(True)
                print('hasEStopBnPushed == False and Stopping soon\n')
                print('Stoping\n')
                print('self.btnEStop_toggle_visibility(False)\n')

                self.steerLabel.setText("X-out of window to terminate!")
                self.isRunning = False
                self.hasEStopBnPushed = False
                self.timer.stop()
                #self.dialUI.value() = self.dialCenter
                #self.steerHoldValue = self.dialUI.self.dial.value()
            else : #assumed self.isRunning == False:
                print('hasEStopBnPushed == False and Starting\n') 
                #App.Console.PrintMessage
                self.btnEStop_toggle_visibility(True)
                self.btnStarter.setText('Stop') 
                print('Starting\n')
                print('self.btnEStop_toggle_visibility(True)\n')
                self.isRunning = True
                self.hasEStopBnPushed = False
                self.steerLabel.setText("Rotate  dial handle Port/Starboard to steer")
                #self.timer.start(self.millisecond)
                #self.dialUI.value() = self.dialCenter
        else:
	        #Assume hasEStopBnPushed == True
            self.btnEStop_toggle_visibility(False)
            if self.isRunning == True:
                print('Emergency Stop.  Full Power-On Reset Required.\n')
                self.steerLabel.setText("STOP!! Vehicle Not Drivable! Abandon Vehicle!")
                self.isRunning = False
                self.hasEStopBnPushed = True
            else: #assumed hasEStopBnPushed == False
                print('Emergency Stop is in effect.  Full Power-On Reset Required.\n')
                self.steerLabel.setText("STOP!! Vehicle requires depot level support!")
                self.isRunning = False
                self.hasEStopBnPushed = True


    def btnEStop_toggle_visibility(self,Good2Go):
        #dialReleased()
        """
        logic needs work
        print('reached btnEStop_toggle_visibility')
        if Good2Go == False:
            print('if Good2Go')
            #self.isRunning = False
            self.hasEStopBnPushed = True
            self.btnEStop.setVisibility(False)
            self.dial.setVisibility(False)
            self.slider.setVisibility(False)
            print('Emergency Stop is in effect.  Full Power-On Reset Required.\n')
            self.steerLabel.setText("STOP!! Vehicle requires immediate user level support!")
        else:
            print('Failed to make Good2Go = True')
            self.btnEStop.setVisibility(True)
            self.dial.setVisibility(True)
            self.slider.setVisibility(True)
            self.hasEStopBnPushed = False
            self.button.show()
        """
        pass

    @Slot()
    def on_dial_changed(self, value):
        #App.Console.PrintMessage('Dial Active')
        if self.isRunning:
            if value > self.dialLastValue:
                self.steerLabel.setText("Starboard")
                self.dialLastValue = value
            elif value <  self.dialLastValue:
                self.steerLabel.setText("Port")
                self.dialLastValue = value 
            if  47 <= value <53:
                self.steerLabel.setText("Forward")
                self.dialLastValue = value
        else:    
            self.steerLabel.setText('Click the Start/Stop')
            self.steerLabel.setText("Forward")
            self.dialLastValue = value

        


if __name__ == "__main__":
    #app = QApplication(sys.argv)
    myFooTest = Foo()
    myFooTest.show()
