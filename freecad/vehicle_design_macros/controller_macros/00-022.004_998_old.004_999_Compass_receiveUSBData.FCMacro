# -*- coding: utf-8 -*-
#***************************************************************************
#*                                                                               *
#*   Copyright (c) 1989- 2025 Abbott Analytical Products   <http://abbottanp.com/>*
#*                                                                               *
#* This program is a spike for bringing simple QtDesign layout into the FreeCAD - Abbott
#*    prototyping the invisioned Abiriba_RG  GM EV vehicle 
#*    detailed at: https://abbottanp.com/artifacts/gm_vehicle_WB/index.html.
#*Helpful Sites:
'''
1> See 250323_1103_examples_PySide for AI questions/inputs of valuein building program
2> Specific source https://doc.qt.io/qtforpython-6/examples/example_gui_analogclock.html
       as noted in copyright "The Qt Company Ltd with addaptations for usage on HehJay
3> List of examples https://doc.qt.io/qtforpython-6/examples/example_qml_tutorials_extending-qml_chapter6-plugins.html
4> GNU Radio https://wiki.gnuradio.org/index.php?title=Main_Page
5> Google collection of guages: https://www.google.com/search?q=qt%20gauge%20widget&udm=2&sa=X&ved=0CC0QtI8BahcKEwi4y6ypw-6MAxUAAAAAHQAAAAAQFA&biw=1096&bih=675&dpr=1
6> Others:
    Progress Bar: https://doc.qt.io/qt-5/qml-qtquick-controls-progressbar.html
    The electric vehicle digital dashboard: https://www.youtube.com/watch?v=j6BS3f9LM9I
    Examples: https://qwt.sourceforge.io/controlscreenshots.html
    Gauges: https://www.google.com/search?sca_esv=22ca403608f503d2&sxsrf=AHTn8zqnsGbbSZSL62NyfDk5CaPIcKbYCA:1745458471431&q=circular+gauge+qt+gauge+widget&uds=ABqPDvztZD_Nu18FR6tNPw2cK_RR9uegVYgQNm0A_FIwPHdCgl5EIbfU0vDhivG2URhPgQ6ziH9vp1fWif_4CVhN5cnXQpfMZs6nnc9En4Gyv9QgUDZ3GoDqmHpIfuX8XU-jvsmpHhKlsRyI_UnH8K6jKII8fiFnKjBxn_in83HLO5ji5ZnESMI&udm=2&sa=X&ved=2ahUKEwixs6PBw--MAxVJMlkFHS1aD8YQxKsJegUIhwEQAQ&ictx=0&biw=1096&bih=675&dpr=1
7> Show markings  https://stackoverflow.com/questions/63698714/how-to-show-markings-on-qdial-in-pyqt5-python
8> Slice steering like SquirrelChaser.  https://stackoverflow.com/questions/64639303/how-to-detect-qt-mouse-events-only-over-qpainted-objects

Need to Add
 setNotchesVisible(True) maks along outlin
  setWrapping(False) halts continuous rotation.

Version History
250608_lu 1> Duplicated 0-022.003_996_987_* as 00-022.004_999_* and renamed
            00-022.004_998 with minor renaming change to help locate/select
            .004_998 will impleemnt a new layout such that a radiobox layout
            will be used rather than the two windows and the associated 
            window management.  See earlier dev_swarf for prior notes or at 
            the bottom of this module.  Dropping "def setModeWindow(self):"

'''

import sys
from PySide2 import QtWidgets, QtCore
from PySide2.QtWidgets import (QApplication, QStackedLayout, QComboBox, QWidget, QPushButton, QDial, QSlider, QVBoxLayout, QHBoxLayout, QLabel,QRadioButton)
from PySide2 import QtGui, QtCore
from PySide2.QtGui import QFont, QColor
from PySide2.QtCore import (Qt, Slot, QTimer)
from PySide2.QtCore import Signal, QEvent
from PySide2.QtGui import QCursor

"""
Comment these out to return behavior but drops the gauge-dial
"""
from PySide2.QtCore import *
from PySide2.QtGui import *
"""  
uses these elements
from PySide2 import QtWidgets, QtCore
from PySide2.QtWidgets import (QApplication, QWidget, QPushButton, QSpinBox, QDial, QSlider, QVBoxLayout, QHBoxLayout, QLabel)
""" 
""" for aapReadUSB_Port """
##Thonny 
from PySide2.QtSerialPort import QSerialPort, QSerialPortInfo
from PySide2.QtCore import QIODevice
#from PySide2.QtCore import QObject, Signal, pyqtSignal <<-- import issue
from PySide2.QtCore import QObject, Signal, QTimer
from threading import Thread
from enum import Enum
#import serial
"""
#==>> Python PySide2 What would a class look like for a serial read of the ttyUSB0 port
#Google AI suggestion
#https://www.google.com/search?client=ubuntu-sn&channel=fs&q=Python+PySide2+What+would+a+class+look+like+for+a+serial+read+of+the+ttyUSB0+port
"""

import FreeCAD as App
import FreeCADGui as Gui
#from aapLib import aapReadUSB_Port
#from aapLib import aapNavDial, aap_CompasWidget, aapReadUSB_Port, aapPDB

# aaPDB stuff
from PySide2.QtCore import QObject
import pdb

"""
hold for later use with a FCStd project file
wrkPrjFile   = "_0_001_test"
wrkShapeObj   = 'TBD'      #Let FreeCAD do the naminging work during building
App.setActiveDocument(wrkPrjFile)
App.ActiveDocument=App.getDocument(wrkPrjFile)
Gui.ActiveDocument=Gui.getDocument(wrkPrjFile)
Gui.getMainWindow()  # was showMainWindow
"""



# Application wide variable/flags etc
aapUSB_Port = "/dev/ttyUSB0"

devFlag = True


class cntrlTristate(Enum):
    COMPASS = 0
    USBPAD = 1
    XCARE = 2


class aapPDBmgr(QObject):   ### SerialReader
    def __init__(self,isAapPDBneeded):
        super().__init__()
        self.debug_on = isAapPDBneeded
        if self.debug_on == True:
            #pdb.set_trace()
            print("ln 267 In Debug mode")
        else:
            print("ln 269 Good to go as is")

def breakpoint():
    pass

## see https://doc.qt.io/qtforpython-5/PySide2/QtCore/QThread.html#PySide2.QtCore.PySide2.QtCore.QThread.run
class aapReadUSB_Port(QObject):   ### SerialReader
    data_received = QtCore.Signal(str)   # wasSignal(bytes)
    progress = QtCore.Signal(int)  # Signal for progress
    finished       = QtCore.Signal()     # Signal when task completes


    #old def __init__(self, parent=None):
        #super().__init__(parent)
    def __init__(self, inport):
        super().__init__()

        self.port = inport
        self.isTrafficOn = False
        self.last_dataRead = 'tbd'
        ####self.dataReadChanged.connect(self._emit_custom_signal)


    def setupPort(self):
        self.serial_port = QSerialPort()
        #using "import serial" self.serial_port = serial
        self.serial_port.port = self.port  #'/dev/ttyUSB0'
        self.serial_port.baudrate = 9600
        self.serial_port.read_mSec  = 200
        self.serial_port.setPortName(self.serial_port.port)
        self.serial_port.setBaudRate(QSerialPort.Baud9600)
        self.serial_port.setDataBits(QSerialPort.Data8)
        self.serial_port.setParity(QSerialPort.NoParity)
        self.serial_port.setStopBits(QSerialPort.OneStop)




    def startThreadPort(self):
        self.isTrafficOn = True
        self.thread = Thread(target=self.readPort, daemon=True)
        self.thread.start()
        print('thread start completed')
        self.run()

    def run(self):
        try:
            self.setupPort()
            rtnVal = self.openPort()
            if rtnVal == 1: #open
                rtnVal = 0
                print('readAcrossThread ready to jump to readPort()')
                rtnval = self.readPort()
            if rtnVal == 9:
                self.closePort()
            if rtnVal == 0:
                print('Ooops')
        except Exception as e:
            print(f"Serial error: {e}")
         

    def readPort(self):
        termKnt = 0
        i = 1
        while self.isTrafficOn:
            #print("test for serial_port Ready to Read")
            if self.serial_port.waitForReadyRead(self.serial_port.read_mSec):  # Wait for data with a timeout of 1000ms
                dataFromUSB = self.serial_port.readAll()
                self.progress.emit(i)  # Send progress updates
                #if devFlag: 
                #    print("ln 296 Received:", dataFromUSB.data().decode(),'\n')
                self.data_received.emit(dataFromUSB.data().decode()) # Emit the data
                self.on_dataRead_changed(dataFromUSB.data().decode())
                i += 1
            else:
                if devFlag:
                    stopper = 100   #development quick wait
                else:
                    stopper = 1000 #production/release longer wait
                
                if termKnt > stopper:
                    self.isTrafficOn = False
                    print("Controller Off: emit Finished Signal")
                    self.finished.emit()
                else:
                    termKnt += 1
        return 9


    def closePort(self):
        self.isTrafficOn = False
        self.serial_port.close()

    def openPort(self):
        rtnVal = 0
        print('If Port Opened => Read else bad => rtnVal_2 + halt')
        if self.serial_port.open(QIODevice.ReadWrite):
            print("Port opened successfully")
            self.isTrafficOn = True
            self.serial_port.is_open = True
            rtnAvl = 1
            while self.isTrafficOn:
                 self.readPort()   # halts when there is no input from controller
        else:
            print("Failed to open port")
            self.isTrafficOn = False
            self.serial_port.is_open = False
            self.termKnt = 0
            rtnVal = 2


    def on_dataRead_changed(self, value):
        self.last_dataRead = value
        #if devFlag: 
        #    print("ln 340:: self.last_dataRead: ",value, "\n")

   
'''  
cut for dev
'''  
class aapNavDial(QDial):
    #valueChangedCustom = QtCore.Signal(int)
    valueIsChanging = QtCore.Signal(int)
    mouseHovers = QtCore.Signal(int)
    mouseEnters = QtCore.Signal(int)  #aap Signal
    mouseExits  = QtCore.Signal(int)  #aap Signal

	
    def __init__(self, parent=None):
        super().__init__(parent)
        self.setMinimumSize(200, 200)  #originally from aap0035_003_002/4
        self.setMinimum(0)
        self.setMaximum(100)  
        self.dialCenter = 0  # value of 50 points South
        self.setGeometry(50, 50, 150, 150)
        self.setValue(self.dialCenter) # Initial value
        self.setNotchesVisible(True)
        self.last_value = self.dialCenter
        #self.valueChanged.connect(self._emit_custom_signal)
        ## self.on_value_changed.connect(self._emit_custom_signal)
        self.mouseHovers.connect(self.hoverEvent)
        self.mouseEnters.connect(self.enterEvent)
        self.mouseExits.connect(self.leaveEvent)
        print('ln 408 Unkown reference begin aap0035_003_002 in aapNavDial \n')       

    def paintEvent(self, event):
        #print('paintEvent\n')       
        painter = QPainter(self)
        painter.setRenderHint(QPainter.Antialiasing)

        # Background circle
        painter.setBrush(QColor(50, 50, 50))
        painter.drawEllipse(self.rect().center(), min(self.width(), self.height()) // 2 - 2, min(self.width(), self.height()) // 2 - 2)

        # Needle
        painter.setBrush(QColor(255, 0, 0))
        angle = self.value() / (self.maximum() - self.minimum()) * 360  # Calculate angle
        center = self.rect().center()

        # Needle polygon
        needle_length = min(self.width(), self.height()) // 2 - 10
        p1 = QPoint(center.x(), center.y() - needle_length)
        p2 = QPoint(center.x() + 5, center.y()+30)
        p3 = QPoint(center.x() - 5, center.y()+30)

        # Needle Knob
        polygon = QPolygon([p1, p2, p3])
        painter.translate(center)
        painter.rotate(angle)
        painter.translate(-center)
        painter.drawConvexPolygon(polygon)
        #painter.drawEllipse(self.rect().center(), 25, 25)
        painter.drawEllipse(center.x()-12.5,center.y()+20, 25, 25)

        # Center circle
        painter.setBrush(QColor(255, 255, 255))
        painter.drawEllipse(self.rect().center(), 5, 5)

   ## end from aap0035_003_002
        painter.end()

    #def _emit_custom_signal(self, value):
    #   print('ln 443 custom signal value change')
    #    self.valueChangedCustom.emit(value)
    #250531 redef self.valueIsChanging.emit(value)

    def hoverEvent(self,event):
        #print("Mouse hovering over dial")
        self.setValue(self.last_value)
        self.mouseHovers.emit(9999)
        self.on_value_changed(9999)
        #self._emit_custom_signal(9999)
        self.isDialHot = True       

    def enterEvent(self, event):
         # Code to execute when the mouse leaves the dial
        #print("Mouse entered the dial")
        self.setValue(self.last_value)
        self.mouseEnters.emit(1111)
        self.on_value_changed(1111)
        #self._emit_custom_signal(1111)
        self.isDialHot = True        


    def leaveEvent(self, event):
         # Code to execute when the mouse leaves the dial
        #print("Mouse left the dial")
        self.setValue(self.last_value)
        self.isDialHot = False
        self.mouseExits.emit(1001)
        self.on_value_changed(1001)
        #self._emit_custom_signal(1001)

    def on_value_changed(self, value):
        self.last_value = value
        #print('ln 477 signal on_value_change')
        self.valueIsChanging.emit(value)
        #original self.on_value_change.emit(value)
        #self.on_value_change(value)

        """
        for __init()__
        add         self.dialUI.valueChanged.connect(self.update_steerLabel)
        """
def create_btnEStop(steerLabel, callback):
    button = QPushButton(steerLabel)
    button.clicked.connect(callback)
    button.setStyleSheet("background-color: red;")
    #button.setStyleSheet("font-color: white;")
    button.setGeometry(50, 50, 150, 150)
    # Font and size
    font = QFont("Arial", 34)
    button.setFont(font)
    # Color
    button.setStyleSheet("QPushButton {color: white; background-color: red;}")
    #button.setVisible(False)
    return button



def create_button(steerLabel, callback):
    button = QPushButton(steerLabel)
    button.clicked.connect(callback)
    return button


"""
Hold for future possible use
def create_dial(min_val, max_val, center_val, callback):
    print('create aapNavDial\n')       
    dial = aapNavDial()
    dial.setMinimum(min_val)
    dial.setMaximum(max_val)
    dial.setValue(center_val)
    dial.setNotchesVisible(True)
    dial.lastvalue = center_val
    dial.valueChanged.connect(callback)
    dial.setTracking(True)   #insure value changes with corsor move
    #dial.setVisible(False)
    print('Returning to home plate\n')
    return dial
"""

def create_Accel_Slider(min_val,max_val ,tickpos,callback):
 #   slider = QSlider(min_val, max_val, tickpos)
    slider = QSlider()
    slider.setMinimum(min_val)
    slider.setMaximum(max_val)
    slider.setValue = 0
    slider.TickPosition = 3
    slider.valueChanged.connect(callback)
    #slider.setVisible(False)
    return slider

def create_Fuel_Slider(min_val, max_val,callback):
    slider = QSlider()
    slider.setMinimum(0)
    slider.setMaximum(100)
    slider.TickPosition = 3
    slider.setValue(100)
    slider.valueChanged.connect(callback)
    #slider.setVisible(False)
    return slider


class OpModeGroup(QWidget):
    def __init__(self, parent=None):
        super().__init__(parent)
        #Create OpMode Radio Button Group
        self.btnRadioOpt1 = QRadioButton("Compass Needle Touch (Default)")
        self.btnRadioOpt1.setChecked(True)
        self.btnRadioOpt2 = QRadioButton("USB Control Pad")
        self.opModeLayout = QVBoxLayout()
        self.opModeLayout.addWidget(self.btnRadioOpt1)
        self.opModeLayout.addWidget(self.btnRadioOpt2)



class HehJayDashCntrl(QtWidgets.QDialog):
 
    def __init__(self, parent=None):
        super().__init__(parent)
    #def __init__(self, parent=None):
        #super(HehJayDashCntrl,self).__init__(parent)
        self.aapPDB = aapPDBmgr(False)  #turn-off pdb
        ### 250607 self.aapPDB = aapPDBmgr(True)  #turn-on pdb
        self.mode = cntrlTristate.XCARE
        #250608 self.setMainWindow()
        
        #invoked from setModeWindow()  self.setCntrlWindow()
        self.serial_reader = None
        self.setCntrlWindow()
    """
    def setModeWindow(self):
        self.modeLabel = QLabel("Click to Select Op Mode to Reach Contrl Panel")
        self.btnModeTOUCH = create_button("Touch/Mouse", self.btn4modeTOUCH_clicked)
        self.btnModeUSBPAD = create_button("Control Pad", self.btn4modeUSBPAD_clicked)
        #self.combo4mode = QComboBox()
        #self.combo4mode.addItem("Touch Mouse", cntrlTristate.COMPASS)
        #self.combo4mode.addItem("Control Pad", cntrlTristate.USBPAD)
        #self.combo4mode.addItem("Don't Care", cntrlTristate.XCARE)
        self.modelayout = QVBoxLayout(self)
        self.modelayout.addWidget(self.modeLabel)
        self.modelayout.addWidget(self.btnModeTOUCH)
        self.modelayout.addWidget(self.btnModeUSBPAD)
        #modelayout.addWidget(self.combo4mode)
        #self.combo4mode.currentIndexChanged.connect(self.on_combo4mode_change)

    def btn4modeTOUCH_clicked(self):
        self.mode = cntrlTristate.COMPASS
        print(f"ln 578 Selected Mode: Touch/Mouse on Compass")
        #self.setModeWindow().close
        self.switch_layout()
        current_index = 0  #self.stacked_layout.currentIndex()
        new_index = 1    #if current_index == 0 else 0 # Ternary operator
        self.stacked_layout.setCurrentIndex(new_index)
        self.setCntrlWindow()
        
    def btn4modeUSBPAD_clicked(self):
        self.mode = cntrlTristate.USBPAD
        print(f"ln 588 Selected Mode: Controler Pad")
        #self.setModeWindow().close
        current_index = 1 #self.stacked_layout.currentIndex()
        new_index = 2    #1 if current_index == 0 else 0 # Ternary operator
        self.switch_layout()
        self.stacked_layout.setCurrentIndex(new_index)
        self.setCntrlWindow()
    

    ''' 
    #def on_combo4mode_change(self, index):
    def on_btn4mode_change(self):
        #selected_value = self.combo4mode.itemData(index, Qt.UserRole)
        selected_value = self.mode
        print(f"Selected Value: {selected_value.name} ({selected_value.value})")
        self.setModeWindow().close
        self.setCntrlWindow()
    '''
    """

    def startUSBThread(self):
        print("Starting Controller USB Port")
        self.usblabel.setText("Starting USB...")

        self.serial_reader = aapReadUSB_Port(aapUSB_Port) # Replace with active serial port
        #??? why 2 statements  ln 521 and ln 526
        #self.serial_reader.startThreadPort()  # ln 521
        self.serial_reader.data_received.connect(self.on_data_received)
        self.serial_reader.data_received.connect(self.on_data_received) # Connect signal to base function call
        self.serial_reader.finished.connect(self.task_finished)
        self.serial_reader.progress.connect(self.update_progress)
        self.serial_reader.startThreadPort()  # ln 526
        self.serial_reader.closePort()


    def setCntrlWindow(self):
        # begin chop-out of block
        self.steerLabel = QLabel("ln 645 Click Start Stop to Activate/Halt")
        self.steerDirLbl = QLabel("ln 646 All Head Forward")
        self.accelLbl = QLabel("Speed: mph                               Capacity: KWHr")

        self.btnStarter = create_button("Toggle to Stop", self.on_button_clicked)  # Assumes starting with btn click for Compas or USBPAD
        self.btnEStop   = create_btnEStop("Emergemcy\n Stop", self.on_button_clicked)
        self.btnEStop.clicked.connect(self.btnEStop_toggle_visibility)
        EStoplayout = QHBoxLayout()
        EStoplayout.addStretch()  # Add stretch to push the button to the right
        EStoplayout.addWidget(self.btnEStop, alignment=Qt.AlignRight | Qt.AlignBottom)
        self.hasEStopBtnPushed = False
        self.isRunning = True   #beginning in run-ready stateFalse
        print("self.mode: ", self.mode)
        if self.mode == cntrlTristate.USBPAD:
            print("ln 638 USBPAD Mode\n") 
            self.isDialHot = True 
        elif self.mode == cntrlTristate.COMPASS:
            
            print("ln 642 COMPASS Mode\n") 
            self.isDialHot = True 
        else: # must still be XCARE          
            self.mode = cntrlTristate.COMPASS
            print("ln 646 Forced COMPASS Mode\n") 
            print("ln 647 not allowed XCARE Mode\n") 
            self.isDialHot = True

        """
         100 < 53....Port  <== 50....Forward  ==> Starboard....47  < 0
        """
        self.dialMin = 0
        self.dialMax = 100
        self.dialCenter = 50   #0   50
        #self.dialMin = 100
        #self.dialMax = 0
        #self.dialCenter = 0   #50

        self.dialLastValue =  self.dialCenter
        self.dialActive = False  #dialUI is not active yet.  Mouse needs to hoover over
        #Flags used ot turn messages on/off and control redundant messages
        self.FlipFlagExit = True   #Begins as True: just exited
        self.FlipFlagEnter = False
        self.dialUI = aapNavDial()
        #self.dialUI.valueChangedCustom.connect(self.update_label)
        self.dialUI.mouseHovers.connect(self.dialHovers(9999))
        #self.dialUI.mouseEnters.connect(self.dialActive(1111))
        self.dialUI.mouseExits.connect(self.dialReleased(1001))
        self.dialUI.valueChanged.connect(self.on_dial_changed)
        self.dialUI.valueChanged.connect(self.update_label)
        self.dialUI.setFocusPolicy(Qt.FocusPolicy.StrongFocus) # Allow dial to receive focus
        # end dial aap0035-997
        self.sliderAccel = create_Accel_Slider(0,100,3, self.on_sliderAccel_valueChanged)
        self.sliderFuel =  create_Fuel_Slider(0,100, self.on_sliderFuel_valueChanged)
        # end of block chop-out
        self.radbtnOpModeGroup = OpModeGroup()
        self.cntrl_layout = QVBoxLayout()      #Parent layout
        self.cntrl_layout.addWidget(self.radbtnOpModeGroup)
        self.cntrl_layout.addWidget(self.btnStarter)
        self.cntrl_layout.addWidget(self.steerLabel)
        self.cntrl_layout.addWidget(self.steerDirLbl)
        self.cntrl_layout.addWidget(self.accelLbl)
        dashBoardLayout = QHBoxLayout()
        dashBoardLayout.addWidget(self.sliderAccel)
        dashBoardLayout.addWidget(self.dialUI)
        dashBoardLayout.addWidget(self.sliderFuel)
        #cntrl_layout.addWidget(self.dialUI)
        #cntrl_layout.addWidget(self.sliderAccel)
        #cntrl_layout.addWidget(self.sliderFuel)
        self.cntrl_layout.addLayout(dashBoardLayout)
        self.cntrl_layout.addWidget(self.btnEStop)
        #self.btnStarter = QtWidgets.QPushButton("Start Controller Pad")
        if self.mode == cntrlTristate.COMPASS:
            self.usblabel = QLabel("ln 691 Panel Active... Check Report View")
        elif self.mode == cntrlTristate.USBPAD:
            self.usblabel = QLabel("ln 693 Await CntrlPad Data... Check Report View")
        else:
             self.usblabel = QLabel("ln 695 Awaiting Panel Inputs... Check Report View")
       #cntrl_layout.addWidget(self.btnStarter)
        self.cntrl_layout.addWidget(self.usblabel)
        self.setLayout(self.cntrl_layout)
        #self.btnStarter.clicked.connect(self.startUSBThread)

    @Slot(str)
    def on_data_received(self, data):
        #print(f"ln 421 Received data: {data.decode()}") # Decode to string if needed
        #elf.usblabel.setText(f"ln 422 Received: {data.decode()}")
        print(f"ln 699 Received data: ",data) # Decode to string if needed
        self.usblabel.setText(f"ln 700 Received: ", data_received)

    @Slot(int)
    def update_progress(self, value):
        """Update progress bar on progress signal."""
        print(f"ln 705 Count if USB lines Read: {value}")
        self.progress_bar.setValue(value)
        self.usblabel.setText(f"line read: {value}")

    @Slot()
    def task_finished(self):
        """Handle task completion."""
        print("ln 712 Done with the eggs.")
        self.btnStarter("Click to restart Pad!")
        self.usblabel.setText("Please Sir, one more")
        self.serial_reader = None  # Release reference

    def set_dial_value(self, value):
         self.dial.setValue(value)
    """
    def on_dial_changed(self, value):
        #Reset to 50 when focus changes
        print("ln 694 on_dial_changed")
        if value != 50:
            self.dial.setValue(50)
    """

    @Slot()
    def update_label(self, value):
        """
        Allowed Values/States:
        1001: mouse exits dial-box
        1111: mouse enters dial-box
        9999: mouse hovers over dial-box
        -1:    Waiting
        1:     Forward: 97 - 3 mouse steering generally forward
        4:     Starboard mouse steering right
        96:    Portt mouse steering to left
        """
        #print('update_label\n')
        #250529_1624 
        print("ln 741  update_label is  value: " ,  str(value), '\n')
        if value == 1001:  #Mouse exits  Dial
            # dev print('Cursor not in Dial')
            #print('update_label: value = 1001 Mouse exits  Dial\n')
            if self.FlipFlagExit == False:
                 # dev print("isDialHot Flipping to False")
                 self.FlipFlagExit = True
                 self.FlipFlagEnter = False
            self.steerLabel.setText(f"ln 749 Value: {'Forward'}")
            # dev self.steerLabel.setText(f"Value: {'Forward Now Going Cold 1001'}")
            self.dialUI.setValue(self.dialCenter)
            if self.isDialHot == True:
                self.last_value = self.dialCenter
                print("ln 740 self.last_value:", self.last_value, " ...self.dialLastValue", self.dialLastValue, "\n")
                self.isDialHot = False
                #self.dialUI.setCursor(QCursor(Qt.ArrowCursor))
        elif value == 1111: #Mouse enters Dial setup for fresh turn
            #print('update_label: value = 1111 Mouse enters  Dial\n')
            # dev print('Mouse entered dial')
            if self.FlipFlagEnter  == False:
                # devprint("isDialHot Flipping to True")
                self.FlipFlagEnter = True
                self.FlipFlagExit = False
            self.steerLabel.setText(f"ln 764 Value: {'Forward'}")
            # dev self.steerLabel.setText(f"Value: {'Forward Going Hot '}")
            self.dialUI.setValue(self.dialCenter)
            self.last_value = self.dialCenter
            self.isDialHot = True
            self.dialUI.setCursor(QCursor(Qt.PointingHandCursor))
        elif value == -1:
            # dev print("Welcome.  We are idling")
            print('ln 771 update_label: value = -1 Waiting \n')
            self.steerLabel.setText(f"Value: {'Ready'}")
            # dev self.steerLabel.setText(f"Value: {'Waiting for Good-To-Go'}")
            self.dialUI.setValue(self.dialCenter)
            print("ln 776 self.last_value:", self.last_value, " ...self.dialLastValue", self.dialLastAalue, "\n")
            self.last_value = self.dialCenter  
            self.dialUI.isDialHot = False
            self.FlipFlagExit = True
            self.FlipFlagEnter = False
        elif value == 4:
            breakpoint()
            print("ln 782 Starboard\n")
            self.steerLabel.setText("ln 783 Starboard")
            self.usblabel.setText(f"ln 784 Value: {'Starboard'}")
        elif value == 96:
            breakpoint()
            print("ln 786 Port\n")
            self.steerLabel.setText("ln 787 Port\n")
            self.usblabelabel.setText(f"ln 788 Value: {'Port'}")
        else:   # forced to be 9999
            if self.isDialHot == True:
                # dev 
                breakpoint()
                print('ln 801   isDialHot equals True')
                print('ln 802 update_label: value = ' +str(value) + ' ...Dial is hot \n')
                print("ln 804 old value: ", value, "\n")
                self.steerLabel.setText(f"ln 805 Value: {value}")
                #is_BoundedBy(value,4,50)
                print("ln 807 value: ", value, '\n')
                if value == 4:  #steering to Starboard
                    breakpoint()
                    self.steerLabel.setText("ln 810 Starboard")
                elif value == 96 :  #steering to Port
                    breakpoint()
                    self.steerLabel.setText("ln 813 Port")
                else:
                    breakpoint()
                    self.steerLabel.setText("ln 816 Forward")
                self.last_value = value
                print("ln 818 self.last_value:", self.last_value, " ...self.dialLastValue", self.dialLastValue, "\n")
                print("ln 819 new value: ", self.last_value, "\n")
                
            """
             else:
                self.dialUI.setValue(self.dialCenter)
                self.last_value = self.dialCenter
           """

    @Slot(int)
    #@Slot()
    def dialHovers(self,tstValue):
        #self.dialUI.sliderReleased()
        print('ln 830 Hover over Dial   tstValue:', str(tstValue),'\n')
        #self.steerLabel.setText("Forward")
        self.update_label(tstValue)
        self.dialLastValue = self.dialCenter

 
    @Slot(int)
    #@Slot()
    def dialActive(self,tstValue):
        #self.dialUI.sliderReleased()
        print('ln 840 Dial Now  Active\n')
        self.update_label(tstValue)
        self.steerLabel.setText("Forward")
        self.dialLastValue = self.dialCenter

    @Slot(int)
    #@Slot()
    def dialReleased(self,tstValue):
        #self.dialUI.sliderReleased()
        print('ln 849 Dial Released\n')
        self.steerLabel.setText("Forward")
        self.update_label(tstValue)
        self.dialLastValue = self.dialCenter
        ##  end from aap0035_997


    @Slot()
    def on_sliderAccel_valueChanged(self, value):
        #print('anything!!!\n')
        #if dialReleased() == True:
        print('Speed: ' + str(value)+ ' kph\n')

    @Slot()
    def on_sliderFuel_valueChanged(self, value):
        #print('anything!!!\n')
        #dialReleased()
        print('Battery: ' + str(value)+ ' kwh remaining\n')

    @Slot()
    def update(self):
        #dialReleased()
        self.steerHoldValue = self.dialUI.self.dial.value()
        #App.Console.PrintMessage
        print('Update::   ' + str(self.steerHoldValue) +'\n')




    @Slot()
    def on_button_clicked(self):
        """
        logic needs work 
        """
        print('ln 873   Start/Stop Toggled\n')
        #dialReleased()
        if self.isRunning == True:
            self.btnStarter.setText('ln 876   Stop') 
            self.started = True
        else:
            if self.hasEStopBtnPushed == False:
                self.btnStarter.setText('ln 880 Start') 
                self.started = False 
        if self.hasEStopBtnPushed == False:
            print('ln 883: if hasEStopBtnPushed == False\n')
            
            if self.isRunning == True and self.mode == cntrlTristate.COMPASS:             
                #print
                self.btnStarter.setText('Stop') #need to switch button text 
                self.btnEStop_toggle_visibility(True)
                print('ln 895  hasEStopBtnPushed == False and Stopping soon\n')
                print('ln 896 Stopping\n')
                print('ln 897 self.btnEStop_toggle_visibility(False)\n')

                self.steerLabel.setText("ln 899 X-out of window to terminate!")
                #self.isRunning = False
                #self.hasEStopBtnPushed = False
                #check why there is a timer   self.timer.stop()
                #self.dialUI.value() = self.dialCenter
                #self.steerHoldValue = self.dialUI.self.dial.value()
            elif self.isRunning == True and self.mode == cntrlTristate.USBPAD: 
                self.startUSBThread()  #250522 
                self.btnStarter.setText('ln 901 Stop') #need to switch button text 
                self.btnEStop_toggle_visibility(True)
                #print('hasEStopBtnPushed == False and Navigate with Control Pad\n')
                print('ln 904 A waiting Stop signal\n')
                #print('self.btnEStop_toggle_visibility(False)\n')
                self.steerLabel.setText("ln 906X-out of window to terminate!")
                #self.isRunning = False
                #self.hasEStopBtnPushed = False
                #self.timer.stop()
            
            else : #assumed self.isRunning == False:
                print('ln 948 hasEStopBtnPushed == False and Starting\n') 
                #print
                self.btnEStop_toggle_visibility(True)
                self.btnStarter.setText('ln 951 Label Reset to Stop') 
                print('ln 952 Starting\n')
                print('ln 953 self.btnEStop_toggle_visibility(True)\n')
                self.isRunning = False
                self.hasEStopBtnPushed = False
                self.steerLabel.setText("ln 920 Rotate  dial handle Port/Starboard to steer")
                #self.timer.start(self.millisecond)
                #self.dialUI.value() = self.dialCenter
                #250528 self.timer.stop()

        else:
	        #Assume hasEStopBtnPushed == True
            self.btnEStop_toggle_visibility(False)
            if self.isRunning == True:
                print('ln 929 Emergency Stop.  Full Power-On Reset Required.\n')
                self.steerLabel.setText("ln 930 STOP!! Vehicle Not Drivable! Abandon Vehicle!")
                self.isRunning = False
                self.hasEStopBtnPushed = True
            else: #assumed hasEStopBtnPushed == False
                print('ln 934 Emergency Stop is in effect.  Full Power-On Reset Required.\n')
                self.steerLabel.setText("ln 935 STOP!! Vehicle requires depot level support!")
                self.isRunning = False
                self.hasEStopBtnPushed = True


    def btnEStop_toggle_visibility(self,Good2Go):
        #dialReleased()
        """
        logic needs work
        print('reached btnEStop_toggle_visibility')
        if Good2Go == False:
            print('if Good2Go')
            #self.isRunning = False
            self.hasEStopBtnPushed = True
            self.btnEStop.setVisibility(False)
            self.dial.setVisibility(False)
            self.slider.setVisibility(False)
            print('Emergency Stop is in effect.  Full Power-On Reset Required.\n')
            self.steerLabel.setText("STOP!! Vehicle requires immediate user level support!")
        else:
            print('Failed to make Good2Go = True')
            self.btnEStop.setVisibility(True)
            self.dial.setVisibility(True)
            self.slider.setVisibility(True)
            self.hasEStopBtnPushed = False
            self.button.show()
        """
        pass
 
    @Slot()
    def on_dial_changed(self, value):
        print('ln 966 steerlbl on dial change ==>> Label for Port, Starboard, Forward\n')
        if self.isRunning:
            print("ln 968 self.isRunning: True ")
        else: 
            print("ln 970 self.isRunning: False ")
        if self.isRunning == True:
            checkSteerLblText = self.steerLabel.text()
            print("ln 1009:  steerLabel: ", checkSteerLblText )
            print("ln 1010 self.isRunning: True ")
            print("ln 1077 current dial value: ", str(value),"    self.dialLastValue: ", self.dialLastValue, "\n")
            #if value > self.dialLastValue:
            breakpoint()
            if value > self.dialLastValue:
                print("ln 1015 jumped Port")
                self.steerLabel.setText("ln 1007 Port")
                breakpoint() 
                self.usblabel.setText("ln 1018 Port")
                self.steerDirLbl.setText("ln 1019 Port")
                breakpoint()
                ## 1137 self.update_label(96)
                self.dialLastValue = value
            #elif value <  self.dialLastValue:
            elif value < self.dialLastValue:
                breakpoint()
                print("ln 1026 jumped Starboard")
                self.steerLabel.setText("ln 1027 Starboard")
                breakpoint()
                ## 1137 self.update_label(4)
                breakpoint()
                self.usblabel.setText("ln 1027 Starboard")
                self.steerDirLbl.setText("ln 1028 Starboard")
                self.dialLastValue = value 
            else:
                print("ln 989 Does the bus stop here")
            #if  47 <= value <53:
            if  97 <= value < 3:
                breakpoint()
                #self.steerLabel.setText("Forward")
                print("ln 995 Forward  97 <--> 3")
                self.usblabel.setText("ln 996 Forward  97 <--> 3")
                self.steerDirLbl.setText("ln 996 Forward  97 <--> 3")
                breakpoint()
                self.update_label(1)
                self.dialLastValue = value
            print("ln 999 Reached here")
        else: # not running
            print("ln 1001 skipped isRunning: True  Must not be running:  isRunning = False")    
            self.steerLabel.setText('ln 1002 Click the Start/Stop')
            self.steerLabel.setText("ln 1003 Forward")
            self.dialLastValue = value
    """
    def setMainWindow(self):
        self.setModeWindow()
        self.setCntrlWindow()
        self.stacked_layout = QStackedLayout()
        
        self.widgetMode = QWidget()
        self.widgetMode.setLayout(self.modelayout)
        self.widgetCntrl = QWidget()
        self.widgetCntrl.setLayout(self.cntrl_layout)
        self.stacked_layout.addWidget(self.widgetMode)
        self.stacked_layout.addWidget(self.widgetCntrl)

        # Fake switch Button to switch layouts
        #self.switch_button = QPushButton("Switch Layout", self)
        #self.switch_button.clicked.connect(self.switch_layout)

        # Main Layout
        self.main_layout = QVBoxLayout()
        self.main_layout.addLayout(self.stacked_layout) # Add stackedLayout which now holds both layouts
        #self.main_layout.addWidget(self.switch_button)

        self.setLayout(self.main_layout)

        # Set the initial layout index to 0 (Layout 1)
        self.stacked_layout.setCurrentIndex(0)
        print("ln 962   programtically call:  switch_layout()")
        self.switch_layout()   #force a one-time switch of windows

    def switch_layout(self):
      pass
    """
    """
      dsregard this behavior for time being 
      current_index = self.stacked_layout.currentIndex()
      new_index = 1 if current_index == 0 else 0 # Ternary operator
      print("ln 971 current_index: ", current_index, "\n")
      print("ln 972 new_index:    ", new_index,"\n")
      self.stacked_layout.setCurrentIndex(new_index)
      self.switch_button.setEnabled(False)
      self.switch_button.hide()
      """
      #if self.mode == cntrlTristate.XCARE and current_index == cntrlTristate.COMPASS
     
            
   

"""
def run_dashCntrl():
    #See 250520_lu AI QThread example 
    dial = HehJayDashCntrl()
    dial.exec_()
"""

"""
# In a FreeCAD macro or workbench
if __name__ == '__main__':
  run_dashCntrl()
"""
# In a FreeCAD macro or workbench
if __name__ == '__main__':
    dial = HehJayDashCntrl()
    dial.exec_()



"""
250607_lu 2> Duplicated 996_988 to 996_987. Added steerDirLbl like usb
           1> Return to 00-022.003_996_988
250604_lu 5> Verified and screenprinted usblabel_update even though USB class ot active???
            4> Returned to the last known good responding update_steerLabel.setText as
            250602 00-022.003_996_995_*.FCMacro  copied to *_966_988_*
            Bad things happen with the pdb enabled but then works.
            3> {no joy} Also found:
            https://stackoverflow.com/questions/11836623/pyside-settext-not-updating-qlabel
            2> {no joy} Discovered correct question for issue with label
            ==>> a QLabel .setText does not update but the following print statement updates with same information
            https://www.google.com/search?client=ubuntu-sn&channel=fs&q=a+QLabel+.setText+does+not+update+but+the+following+print+statement+updates+with+same+information
            1> Copy 00-022.003_996_989 to *_996_988_*.  Redefine aapNavDial class 
               dial changes of value.

250601_lu 3> Verified throwing label for Port and Starboard 00-0220.003_996_995*.FCMacro
            Duplicated00-22.003_996_994 from 996_995
            2> Hard coded breakpoint()
            1> Copied 00-022.003_996_996 to _995

250530_lu 1> Duplicated from 00-022.003_996_997. Ran under pdb without issue. Verified the recursive issue is gone.

250529_lu Continue troubleshooting Compass.  Use the switch_layout(self) to replace on_btn_changed()

250528_lu 2> Troubleshooting the Compass
            1>Verified that disable and hide solves the crashing from switching modes.  But it 
            closes pathway to the third switch, i.e Mode_SW -> Compass (Mode_SW not available)
            but USBPAD available from "Start" of Compass.  NOTE: Start btn lable does not 
            change.
            


250527_lu Detail code on mode selection 
           ==>> PySide 2 create and use a set of values like for tristate:  false, true , xcare
           https://www.google.com/search?q=PySide+2+create+and+use+a+set+of+values+like+for+tristate%3A++false%2C+true+%2C+xcare&client=ubuntu-sn&hs=TD1&sca_esv=4fa71b8dbfa83ed9&channel=fs&sxsrf=AE3TifNx9sTeOE6d08UxQLg4RetoD4ViRA%3A1748360574601&ei=ft01aOu4JIOv5NoPoY3juQY&ved=0ahUKEwjr7_PX_sONAxWDF1kFHaHGOGcQ4dUDCBA&uact=5&oq=PySide+2+create+and+use+a+set+of+values+like+for+tristate%3A++false%2C+true+%2C+xcare&gs_lp=Egxnd3Mtd2l6LXNlcnAiT1B5U2lkZSAyIGNyZWF0ZSBhbmQgdXNlIGEgc2V0IG9mIHZhbHVlcyBsaWtlIGZvciB0cmlzdGF0ZTogIGZhbHNlLCB0cnVlICwgeGNhcmVIomFQ7BJYlFZwAXgAkAEAmAFsoAHpC6oBBDE0LjS4AQPIAQD4AQGYAgGgAhPCAgoQABiwAxjWBBhHmAMAiAYBkAYIkgcBMaAH1jqyBwC4BwA&sclient=gws-wiz-serp
           wrong-->error==>> PySide 2 for one app start one qlayout close it and then open second layout
           https://www.google.com/search?client=ubuntu-sn&channel=fs&q=PySide+2+for+one+app+start+one+qlayout+close+it+and+then+open+second+layout+
           ==>> works PySide2.QtWidgets.QStackedLayout' object has no attribute 'addLayout'
           https://www.google.com/search?client=ubuntu-sn&channel=fs&q=PySide2.QtWidgets.QStackedLayout%27+object+has+no+attribute+%27addLayout%27

250526_lu 2> Implemented mode selection and tied USB CnrtrlPad to HehJay Cntrl Panel
          1> Duplicated from 00-022.003_999*.FCMacro

250523_lu Found ln 521 and ln 526 to be duplicates 
           all works well after dropping ln 521

250522_lu Complete integration and tested.  Need to post USB data to base class, parser, and send changes 
          (direction_xy, speed, and button function letter) to control panel/vehicle behavior.  Basic USB data
          (lines of text data xxx_yyy_123_@A) are not purculating through to base class but integer progress 
          and string 

250521_lu 
         4> Achieve a "basic" runnable 00-022.003_*.FCMacro but not completely linked 
         3> Reintegrate parts of 
         2> Failed to see the Finish signal slide trhu the thread
         1> Could not obtain same code example with same query.  Tweaked 00_024_*.FCMacro until runable again
         using https://www.google.com/search?q=what+would+a+FreeCAD+project+look+like+for+pyside+2+QThread+from+FreeCADGui+environment&client=ubuntu-sn&sca_esv=7fd10217c7be2381&channel=fs&sxsrf=AHTn8zqwN8XfYXX--gYeztIwhVvoUK2QTw%3A1747774600754&ei=iOwsaILeLdef5NoPgIDL6AY&ved=0ahUKEwiCwubh97KNAxXXD1kFHQDAEm0Q4dUDCBA&uact=5&oq=what+would+a+FreeCAD+project+look+like+for+pyside+2+QThread+from+FreeCADGui+environment&gs_lp=Egxnd3Mtd2l6LXNlcnAiV3doYXQgd291bGQgYSBGcmVlQ0FEIHByb2plY3QgbG9vayBsaWtlIGZvciBweXNpZGUgMiBRVGhyZWFkIGZyb20gRnJlZUNBREd1aSBlbnZpcm9ubWVudEiAiwNQhm1Yj-UCcAF4AJABAJgBkAGgAaUSqgEEMC4yMLgBA8gBAPgBAZgCEaACoBDCAgsQABiABBiwAxiiBMICCBAAGIAEGKIEwgIFEAAY7wXCAgoQIRigARjDBBgKwgIIEAAYogQYiQWYAwCIBgGQBgOSBwQxLjE2oAeUVrIHBDAuMTa4B5gQ&sclient=gws-wiz-serp
         Had to Search History for Yesterday's AI Find.  Probably because the AI learned a new error in behavior.
         

250520_lu ==>> what would a FreeCAD project look like for pyside 2 QThread from FreeCADGui environment
         https://www.google.com/search?q=what+would+a+FreeCAD+project+look+like+for+pyside+2+QThread+from+FreeCADGui+environment&client=ubuntu-sn&sca_esv=7fd10217c7be2381&channel=fs&sxsrf=AHTn8zqwN8XfYXX--gYeztIwhVvoUK2QTw%3A1747774600754&ei=iOwsaILeLdef5NoPgIDL6AY&ved=0ahUKEwiCwubh97KNAxXXD1kFHQDAEm0Q4dUDCBA&uact=5&oq=what+would+a+FreeCAD+project+look+like+for+pyside+2+QThread+from+FreeCADGui+environment&gs_lp=Egxnd3Mtd2l6LXNlcnAiV3doYXQgd291bGQgYSBGcmVlQ0FEIHByb2plY3QgbG9vayBsaWtlIGZvciBweXNpZGUgMiBRVGhyZWFkIGZyb20gRnJlZUNBREd1aSBlbnZpcm9ubWVudEiAiwNQhm1Yj-UCcAF4AJABAJgBkAGgAaUSqgEEMC4yMLgBA8gBAPgBAZgCEaACoBDCAgsQABiABBiwAxiiBMICCBAAGIAEGKIEwgIFEAAY7wXCAgoQIRigARjDBBgKwgIIEAAYogQYiQWYAwCIBgGQBgOSBwQxLjE2oAeUVrIHBDAuMTa4B5gQ&sclient=gws-wiz-serp
         see 00_024_SuperThread_*.FCMacro for working app

250515_lu Still tweaking the USB flow:
	    1> From prompt 
	       tom@laptop:~$ ls /dev/ttyUSB*
            /dev/ttyUSB0
        2> Run 00-022receive*.FCMacro 
        2.1> If proper USB commo connection: 
             16:49:20  Good to go as is
             16:49:20  If Port Opened else bad
             16:49:20  Port opened successfully
             16:49:20  ln 260 Received: -20_-18_22_@ 
             -20_-18_22_@ 
             -20_-18_22_@ 
             16:49:21  ln 260 Received: -20_-18_22_@ 

        2.2> If not good connection 
             16:35:13  Good to go as is
             16:35:13  If Port Opened else bad
             16:35:13  Failed to open port
             pops FreeCAD text label "Wating for data...C  Check Report View"
        2.3> check class HehJayDashCntrl() for 
             self.serial_reader = aapReadUSB_Port("/dev/ttyUSB?") ? = 0..9


250514_lu Running well now.
        ==>> how to read Python PySide2 What would a class look like for a serial read of the ttyUSB0 port
        https://www.google.com/search?client=ubuntu-sn&channel=fs&q=Python+PySide2+What+would+a+class+look+like+for+a+serial+read+of+the+ttyUSB0+port


250512_lu Verified that this works well.  Found one minor issue related to the serial origin error

250503_lu Reuse 00-018_classSerialRead by following AI closer by rewiting class aapReadUSB_Port

250501_lu Try to integrate AI poffered solution ==>> PySide 2 PySerial class reads ttyUSB0 how would the program make that data available for the base class
         https://www.google.com/search?client=ubuntu-sn&channel=fs&q=PySide+2+PySerial+class+reads+ttyUSB0+how+would+the+program+make+that+data+available+for+the+base+class
         Cut and paste from AI example to fit my situation

250430_lu Integrate USB0 AAP Controler into display screen features and behavior


250425_lu Tested aap0035_994 first to verifiy functionality.  Added Acceleration and Fuel sliders in a layout
         with Dial, buttons, and label.  Experimented with Num Lock On/Off for Acceleration.  Maybe the 
         Squirrel Chaser control box is the most workable solution at the moment.

250424_lu Return to active troubleshooting.  The (200,200) version was found to have the 
        self.hasEStopBtnPushed = False and self.isRunning = False missing from __init__().  Tested 
        well after that.
 
250422_lu Troubleshooting the aapNavDial class and its variantwith aap0035_003_004
        which works well on a simple subclassing.
        Start with aap0035_003_004 and then build aap0035_995 from 996 to see what breaks 
        the working dial

250421_lu Incorporate lessons from aap0035_003_002_compass.FCMacro into aapNavDial
        Grub: PySide2 QDial needle draw/paint
        AI: https://www.google.com/search?client=ubuntu-sn&channel=fs&q=PySide2+QDial+needle+draw%2Fpaint
            I believe I saw this same basic object example in the QtForm, https://wiki.python.org/, or https://doc.qt.io/....
            The one I copied used "self.setMinimumSize(100, 100)" in the __init__() which the AI does not.
            That setMinimumSize was adjusted to 200,200 and test without incident.
 
250419_lu Introduce operational performance simulation:
        Assumptions: Flat, Hard Dirt, Aerodynamic = 0 until 55mph Coff of Friction Force = mu * N
                       See Holy Grail of AWD System Rivian R1T video of article 4.56 and 6.56 for discussion for mu
                       https://insideevs.com/news/593277/engineering-explained-talks-rivian-r1t-holy-grail-awd-systems/
        Variables considered 
            Service Weight: Vehicle estimate, crew of two, combat load for three days.
            Surface: Dry Hard, see Rivian study
            Slope: Flat, Slopes Up, Slopes Down
            Vehicle KWH/MPH Pre Aerodynamic 0-55 mph
            Vehicle KWH/MPH Post Aerodynamic 55 to 75 mph
        Integration and unit testing completed

250418_lu Begin integrate aap0035_hehJayDrvrControl_999.FCMacro with the aap0035_997_customSignal4Dial.FCMacro
        dial behavior.


250415_lu (abstracted from aap0035_0097customSignal4Dial)
       Works well with mouse and numpad
       With Left mouse 
       start:: run app/macro
       reset:: move mouse out of dial area

              port::                  starboard::
       step moves
              left (port pad)         right (port pad)   NOTE: right pad used for accelerator
              left arrow              right arrow
              4/2 numpad              6/8 numpad
              mouse roller            mouse roller
       rapid jumps
              page down               page up
              pg dn                   pg up
       position jumps
              port: minimum           starboard: maximum      
              home


250412_lu Continue journey.
        Grub: PySide2 for a dialog form with a QWidget object that inherets from QDial what custom signals are required to signal the event of a mouse entering the dial so that a connection can be made to a Form's function 
        https://www.google.com/search?client=ubuntu-sn&channel=fs&q=PySide2+for+a+dialog+form+with+a+QWidget+object+that+inherets+from+QDial+what+custom+signals+are+required+to+signal+the+event+of+a+mouse+entering+the+dial+so+that+a+connection+can+be+made+to+a+Form%27s+function+
        Grub: PySide2 example using widget that inherets QDial but uses custom signals to connect to slots in a dialog form.
        AI gave close model that worked.  But.. did not treanslate to target aap0035_...
        https://www.google.com/search?client=ubuntu-sn&channel=fs&q=PySide2+example+using+widget+that+inherets+QDial+but+uses+custom+signals+to+connect+to+slots+in+a+++++++++++dialog+form.

250411_lu Implemented leaveEvent handling usig by building aapLib aapDial class
        Grub: PySide2 what are the supported types for custom signal connect     self.dialUI.mouseEnters.connect(self.dialActive) <class 'TypeError'>: 'PySide2.QtCore.QObject.connect' called with wrong argument types:   PySide2.QtCore.QObject.connect(aapDial, str, bool) Supported signatures:
        https://wiki.qt.io/Qt_for_Python_Signals_and_Slots
        Grub: Freecad Python QWidget.QDial leaveEvent() AI example as guide
        https://www.google.com/search?client=ubuntu-sn&channel=fs&q=Freecad+Python+QWidget.QDial+leaveEvent%28%29
        Grub: Freecad PySide2 QWidget.QDial leaveEvent()
        https://www.google.com/search?q=Freecad+PySide2+QWidget.QDial+leaveEvent%28%29&client=ubuntu-sn&hs=dqi&sca_esv=0312fbabf4daa587&channel=fs&sxsrf=AHTn8zpAEhiUi8UK_xhOhCAU6DyolWR0PQ%3A1744397407552&ei=X2T5Z8G4IbOhiLMPxqLNyAY&ved=0ahUKEwiB5Mve0tCMAxWzEGIAHUZRE2kQ4dUDCBA&uact=5&oq=Freecad+PySide2+QWidget.QDial+leaveEvent%28%29&gs_lp=Egxnd3Mtd2l6LXNlcnAiKkZyZWVjYWQgUHlTaWRlMiBRV2lkZ2V0LlFEaWFsIGxlYXZlRXZlbnQoKTIFECEYoAEyBRAhGKABMgUQIRigATIFECEYoAFIoZ0sUJmSKVj9rClwAngAkAEAmAFqoAGUB6oBAzguMrgBA8gBAPgBAZgCDKAC5wfCAgsQABiABBiwAxiiBMICCBAAGLADGO8FwgIIEAAYgAQYogTCAgUQABjvBcICBxAjGLACGCfCAggQIRigARjDBJgDAIgGAZAGBZIHAzguNKAHmyGyBwM2LjS4B9kH&sclient=gws-wiz-serp
        Grub: PySide2QWidget.QDial leaveEvent() document emit signal
        https://www.google.com/search?q=PySide2QWidget.QDial+leaveEvent%28%29+document+emit+signal&client=ubuntu-sn&sca_esv=cdd70d77cbc6b9e0&channel=fs&sxsrf=AHTn8zr3bc3mTqZWfLN-qXQ-CyS1kptslA%3A1744403673833&ei=2Xz5Z9-3MpnQ5NoP7LjwwQk&ved=0ahUKEwifiMuK6tCMAxUZKFkFHWwcPJgQ4dUDCBA&uact=5&oq=PySide2QWidget.QDial+leaveEvent%28%29+document+emit+signal&gs_lp=Egxnd3Mtd2l6LXNlcnAiNlB5U2lkZTJRV2lkZ2V0LlFEaWFsIGxlYXZlRXZlbnQoKSBkb2N1bWVudCBlbWl0IHNpZ25hbDIHECEYoAEYCjIHECEYoAEYCjIFECEYqwIyBRAhGKsCMgUQIRirAkjxQlCcAljUJ3ABeAGQAQCYAagBoAGyDKoBBDAuMTK4AQPIAQD4AQGYAg2gAqoNwgIKEAAYsAMY1gQYR5gDAIgGAZAGCJIHBDEuMTKgB_JUsgcEMC4xMrgHmw0&sclient=gws-wiz-serp
250330_lu Issue with Slider
python  QSlider value change
https://stackoverflow.com/questions/43152489/pyqt5-qslider-valuechanged-event-with-delay

"""
