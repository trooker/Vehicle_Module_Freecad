'''
Open a window, reading its layout from *.ui file
same as aap0035_test001_popUi_file but does nothing 
'''
import FreeCAD,FreeCADGui,Part
from PySide import QtGui, QtCore
import sys
from PySide2.QtWidgets import (QApplication, QWidget, QPushButton, QDial, QSlider, QVBoxLayout, QHBoxLayout, QLabel)
from PySide2.QtGui import QFont, QColor
from PySide2.QtCore import (Qt, Slot, QTimer)



path_to_ui = os.path.dirname(__file__) + "/aap0037_hehJayAccRejCheckBx.ui"

class Ui_MainWindow(object):
    def setupUi(self, MainWindow):
        self.centralWidget = FreeCADGui.PySideUic.loadUi(path_to_ui)
        MainWindow.setCentralWidget(self.centralWidget)

    @Slot()
    def update(self):
         #self.steerHoldValue = self.dialUI.self.dial.value()
         #App.Console.PrintMessage
         print('Update::   ' + str(50) +'\n')


    @Slot()
    def on_sliderAccel_valueChanged(self, value):
        #print('anything!!!\n')
        print('Speed: ' + str(value)+ ' kph\n')

    @Slot()
    def on_sliderFuel_valueChanged(self, value):
        #print('anything!!!\n')
        print('Speed: ' + str(value)+ ' kwh remaining\n')




MainWindow = QtGui.QMainWindow()
ui = Ui_MainWindow()
ui.setupUi(MainWindow)
MainWindow.show()
