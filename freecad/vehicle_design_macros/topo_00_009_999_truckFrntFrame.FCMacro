# -*- coding: utf-8 -*-
#***************************************************************************
#*                                                                               *
#*   Copyright (c) 1989- 2024 Abbott Analytical Products   <http://abbottanp.com/>*
#*                                                                               *
#* This program parameterically builds the suspension truckFrame port components for 
#*     supporing the chassis assembly in roll-out ready state (less defined 
#*     steering system) to use for prototyping the invisioned Abiriba_RG  GM 
#*     EV vehicle detailed at: 
#*     https://abbottanp.com/artifacts/gm_vehicle_WB/index.html.
#* Helpful references:
#* Flip vector 90: https://limnu.com/sketch-easy-90-degree-rotate-vectors/
#*      (X, Y, Z) flips 90 using (Z, Y, -X)
#*     	Base.Vector(0,-TOWER_HEIGHT,0) to (0,0,TOWER_HEIGHT)
#*  3D rotation https://en.wikipedia.org/wiki/Rotation_matrix
#*  Topographical scripting https://wiki.freecad.org/Topological_data_scripting
"""
This macro is abstracted stepwise from from Example: Pierced box 
	https://wiki.freecad.org/Topological_data_scripting
	and merged with 00_990_chassisDimensionPlay_yzPlaneAdjust.FCMacro 
	derived from LES-Tower.py to fabricate the chassis shape/solid
	
241224 lu borrowed extensively from the topo_00_008_999*.FCMacro

"""



# remove comment when implemented: from topoChassisToolbox import chassisData, chassisTool
import pdb, math              # python debugger  see python_gdb.sh for shell script
import FreeCAD as App
import Part, math,Draft
import numpy as np
from FreeCAD import Base




__title__="TruckFront Port: Building Front Assembly Suspension System Components of an Exo Cage Vehicle With A Macro"
__author__ = "Lucca Uzzo"
__url__ = "http://abbottanp.com"

#testing for trigger for develpment as a .FCMacro rather than .py
### STEP 1: create, save, close, then invoke/activate new project file
#wrkPrjFile ="spike_001"  #241220_lu"_00_998_a994_controlArmLowerFrntPort_bushings_topo_00_007"
wrkPrjFile   = "_00_858_999_subassySuspensionTruckFrontPort"
wrkShapeObj   = 'Shape'      #Let FreeCAD do the naminging work during building
# dev wrkPrjFile = "_03_963_chassis_topoScripting_cabin_mainBuild"   # copy Project file "label" from property and replace first character with underscore
App.setActiveDocument(wrkPrjFile)
App.ActiveDocument=App.getDocument(wrkPrjFile)
Gui.ActiveDocument=Gui.getDocument(wrkPrjFile)
#end of testing block


sf = 126.4 / 5.455   #scale factor: set by desired dimensions, 
					#	proposed gm_vehilce images and layout of 
					# 	LEW-Tower.py model
df = .6              # design factor
dfslf = 1.00         # Swag based on 057 view of vehicle + 000_799
dfcbfca = .5			# Swag based for cross members of control arm


def toMM(value):
	# Convert gawdawful imperial to mm
	# 126.4 = 5.455 * sf
	return (value * 25.4 * sf)
	
def toMM_pipeDia(value):
	return (value * 25.4 *sf)  


#CHASSIS_RUN = toMM(2.65)  # was 5.455  looks good at 3.25..3.80  squared at 4.0
#CHASSIS_AFT_SPAN = toMM(1.05)#toMM(1.209)    #2.65)  #was 1.209
CHASSIS_BOW_SPAN = toMM(0.8)   #was .919

PIPE_SUSPEN_ControARMDIAMETER = toMM_pipeDia(0.114*df*1.5)
PIPE_SUSPEN_ControARMRADIUS = PIPE_SUSPEN_ControARMDIAMETER / 2.0



"""
see topo_00_007 for example using makePolygon, rotate, transforms, 
 makeshell, makesolid, etc.
"""

FORCE_OPN			 = 40
#not used
FRNT_CONTROLARM_UPPER = 40
FRNT_CONTROLARM_LOWER = 41
REAR_CONTROLARM_UPPER = 60
REAR_CONTROLARM_LOWER = 61

#CONTROLARM_DROP = toMM(-11)#-CHASSIS_AFT_DEPTH or distance between upper/lower control arms
#CONTROLARM_MOVE = toMM(-.085)  # by trial and error centering on xa,ya,za

"""
Derived from 000_858_999 sketch using:
1> A2Plus to create a dummy assy of 
000_799_993
000_859 
000_860
2> A suitable box sketch was generated.  
3> Then the dummy assy was removed
4> Shapes were generate by this topo 
Usage: Use A2Plus to import Port/Starboard to 000_799_993

Raw 
(0,0,0)					#Sketch.Vertex1
(0,0,-430.987)			#Sketch.Vertex2
(0,367.833,-430.987)	#Sketch.Vertex3
(0,367.833,0)			#Sketch.Vertex4


1----------4
|          |
|          |
2----------3


"""
pts4Opn = [  # ndx ?* where * indicates start for shape
App.Vector(0,0,0),     #ndx 0 Sketch.Vertex1	 Shape0.1
App.Vector(0,0,-430.987),    #ndx 1 Sketch.Vertex2	 Shape0.2
App.Vector(0,0,-430.987),    #ndx 2 Sketch.Vertex2	 Shape1.1
App.Vector(0,367.833,-430.987),    #ndx 3 Sketch.Vertex3	 Shape1.2 
App.Vector(0,367.833,-430.987),    #ndx 4 Sketch.Vertex3	 Shape2.1
App.Vector(0,367.833,0),    #ndx 5 Sketch.Vertex4	 Shape2.2
App.Vector(0,367.833,0),    #ndx 6 Sketch.Vertex4	 Shape3.1
App.Vector(0,0,0)]     #ndx 7 Sketch.Vertex1	 Shape3.2




class OpnMgr(object):   #no longer child of ChassisLeg
#class ChassisArch(object):   #no longer child of ChassisLeg	# def setupArchHndlr(pts, subChassisID):
	def __init__(self, pts, subChassisID):  #xa, ya, za, xb, yb, zb, subChassisID):
		rtnMessage = "Nobody Home\n"
		if subChassisID == FORCE_OPN:
			self.fabComponent(pts4Opn)
		'''not used 
		if subChassisID == FRNT_CONTROLARM_UPPER:
			self.fabControlArm(ptsPortFrntSuspensionUpper)
		if subChassisID == FRNT_CONTROLARM_LOWER:
			self.fabControlArm(ptsPortFrntSuspensionLower)
		if subChassisID == REAR_CONTROLARM_UPPER:
			self.fabControlArm(ptsPortRearSuspensionUpper)
		if subChassisID == REAR_CONTROLARM_LOWER:
			self.fabControlArm(ptsPortRearSuspensionLower)
		'''
		rtnMessage = "\ndone\n"
		#App.getDocument(wrkPrjFile).recompute()
		App.Console.PrintMessage(rtnMessage)


	def fabComponent(self,pts4Wrk):
		#See Example3 of spike 005_999_spline_pipe.FCStd 
		#	and Macro 005_999_buildsplinePipe.FCMacro
		np_Arr   = np.array(pts4Wrk)  #vLoc
		#load from 0: loopNdx = 0  
		ShapePairNdx = 0 #ndx for first Vertex1 of four vertex shape
		ShapeQty = 4 #2 #7 #number of shapes beginning with 0 
		for ShapePairNdx in range(ShapeQty):
			zAngle = 90 #270
			if ShapePairNdx == 0:
				startArrayNdx = 0	# look for arry index pointer to first vertex
				zAngle += 0				# of cylinder to build Vertex1 and Vertex2
			if ShapePairNdx == 1:
				startArrayNdx = 2 # was1	# Vertex2 to Vertex3
				zAngle += 0
			if ShapePairNdx == 2:
				startArrayNdx = 4	#Vertex 3 to Vertex 4
				zAngle += 0
			if ShapePairNdx == 3:
				startArrayNdx = 6	#Vertex 5 to Vertex
				zAngle += 0
			#if ShapePairNdx == 4:
			#	startArrayNdx = 8	#Vertex 6 to Vertex7
			#	zAngle += 180
			pntNdx     = startArrayNdx
			wrkArrNa   = np_Arr[pntNdx]
			xa         = wrkArrNa[0]		#yields the x-axis vector component of bow 2d cross-section	 
			ya         = wrkArrNa[1]		#yields the sections length from aft to bow
			za         = wrkArrNa[2]	
			wrkArrNb   = np_Arr[pntNdx+1]# jump to next row in the array
			xb         = wrkArrNb[0]		#yields the x-axis vector component of bow 2d cross-section	 
			yb         = wrkArrNb[1]		#yields the sections length from aft to bow
			zb         = wrkArrNb[2]	
			App.Console.PrintMessage("wrkArrNa:: xa,ya, za\n")
			App.Console.PrintMessage(wrkArrNa)
			App.Console.PrintMessage("\n")
			# erase swarf
			cylinderLength = self.distance(xa, ya, za, xb, yb, zb)
			self._tube = Part.makeCylinder(PIPE_SUSPEN_ControARMRADIUS,cylinderLength)
			self._tube.translate(App.Vector(xa, ya, 0))
			##self._tube.rotate(App.Vector(xa, ya, za),App.Vector(1, 1, 0), targetAngle)

			#App.Console.PrintMessage('Check for Port/Starboard required placement\n')
			if ShapePairNdx == 0:
				self._tube.rotate(App.Vector(xa, ya, za),App.Vector(1,0, 0 ), zAngle)
				self._tube.rotate(App.Vector(xa, ya, za),App.Vector(1,0, 0 ), zAngle)
			if ShapePairNdx == 1:
				self._tube.rotate(App.Vector(xa, ya, za),App.Vector(0,0, 1), zAngle)
				self._tube.translate(App.Vector(0, 0, za))
				zAngle = -90
				self._tube.rotate(App.Vector(xa, ya, za),App.Vector(1,0, 0), zAngle)
			if ShapePairNdx == 2:
#				self._tube.rotate(App.Vector(xa, ya, za),App.Vector(0,1, 0 ), zAngle)
				self._tube.translate(App.Vector(0, 0, za))
			if ShapePairNdx == 3:
				self._tube.rotate(App.Vector(xa, ya, za),App.Vector(1,0, 0 ), zAngle)
			Part.show(self._tube)
			#self._tube = super().__init__(xa,ya, za, xbe, ybe, zbe, CHASSIS_CABIN_STARBOARD)
			#use with while loopNdx -= 1

	#https://stackoverflow.com/questions/20184992/finding-3d-distances-using-an-inbuilt-function-in-python
	def distance(self, x1, y1, z1, x2, y2, z2):
		e = 0.0
		euclidDis = math.sqrt((x2 - x1)**2 + (y2 - y1)**2 + (z2 - z1)**2)
		return euclidDis

"""
	def getAngle(self, pnt1, pnt2,eDistance):
		cosValue = (pnt2 - pnt1)/eDistance
		return cosValue
     
	def findEuclidPoint(self, x1, y1, z1, x2, y2, z2):
		euclidDis = self.distance(x1, y1, z1, x2, y2, z2)
		App.Console.PrintMessage("d Distance from pnt1 to pnt2 in 3D\n" )
		App.Console.PrintMessage(euclidDis)
		App.Console.PrintMessage("\n")
		alpha = self.getAngle(x1,x2,euclidDis)
		beta  = self.getAngle(y1,y2,euclidDis)
		gamma = self.getAngle(z1,z2,euclidDis)
		App.Console.PrintMessage("cosAngles_values\n")
		App.Console.PrintMessage(Base.Vector(alpha, beta, gamma))
		App.Console.PrintMessage("\n")
		xdif   = alpha / euclidDis
		ydif   = beta  / euclidDis
		zdif   = gamma / euclidDis
		#xdif = x1 - x2e
		x2e   = x1 - euclidDis * alpha
		y2e   = y1 - euclidDis * beta
		z2e   = z1 - euclidDis * gamma
		return App.Vector(x2e, y2e, z2e)
"""

def controlArmSection():
	arch40Assign = OpnMgr(pts4Opn, FORCE_OPN)	
#	arch40Lower = ControlArmMgr(ptsPortFrntSuspensionLower, FRNT_CONTROLARM_LOWER)
#	arch40Upper = ControlArmMgr(ptsPortFrntSuspensionUpper, FRNT_CONTROLARM_UPPER)
#	arch60Upper = ControlArmMgr(ptsPortRearSuspensionUpper, REAR_CONTROLARM_UPPER)
#	arch60Lower = ControlArmMgr(ptsPortRearSuspensionLower, REAR_CONTROLARM_LOWER)



#UpperStrutMount()
#Coil_Spring()
#Strut_Assembly()
#controlArm_Bushing()
controlArmSection()
#BallJoints()
