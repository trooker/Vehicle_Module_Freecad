# -*- coding: utf-8 -*-
#***************************************************************************
#*                                                                               *
#*   Copyright (c) 1989- 2024 Abbott Analytical Products   <http://abbottanp.com/>*
#*                                                                               *
#* This program parameterically builds a the shock absorbor brace subassy
#*		for the exo cage in roll-out ready state (less defined steering) to use for 
#*     prototyping the invisioned Abiriba_RG  GM EV vehicle 
#*     detailed at: https://abbottanp.com/artifacts/gm_vehicle_WB/index.html.
#*Helpful Sites:
#*  Topographical scripting https://wiki.freecad.org/Topological_data_scripting
#*	Fuse/Union of Selected components
#*	  https://forum.freecad.org/viewtopic.php?t=4137 Re: Fuse multiple parts in 
#*		python macro fails Post by wmayer » Mon Jun 10, 2013 with AAP adjustments
#*	Part Rotation:  Re: how to rotate an object (placement) by yorik 02/06/2012  
#*		https://forum.freecad.org/viewtopic.php?style=5&t=2213
#*		Alternately used LES_Tower style rotation used in topoChassisFrame.py line 204
#*		as seen Ln 204 	#circle.rotate(App.Vector(0, 0, 0),App.Vector(0, 0, 1), 90)
#*		and modified for FrontChassis rotate of 7.5 degrees about X-axis not Z-Axis
#*
#* Change History
#* 250102 inital adaption of the macro: topoChassis_001_strutBuildGM_vehicle_996_FrntChassis_Part.FCMacro
#*		This adaption fuses the shock abosrbor and brace.
#*
#*** Things That Go Bump In THe Night:
#***


#uncomment for usage:
from topo_00_016_998_suspensionFrontConeBrace import coneBraceFront    #, rearChassisSection
#uncomment for usage:
#from topoChassisCabin import cabinChassisSection
import FreeCAD as App



__title__="Front Cone Brace Subassy for the Shock Absorbers"
__author__ = "Lucca Uzzo"
__url__ = "http://abbottanp.com"



#testing for trigger
### STEP 1: create, save, close, then invoke/activate new project file
#* 250102_lu 
wrkPrjFile = "_00_779_998_suspensionShock_ConeBraceFront"
wrkShapeObj   = 'Shape'      #Let FreeCAD do the naminging work during building




App.setActiveDocument(wrkPrjFile)
App.ActiveDocument=App.getDocument(wrkPrjFile)
#Gui.ActiveDocument=Gui.getDocument(wrkPrjFile)


def getStri(startNdx):
		if startNdx < 10 :
			stri = '00' + str(startNdx)
		else:
			stri = '0' + str(startNdx)
		return stri

def removeShape(wrkShapeTarget):
	### Begin command Std_Delete
	App.getDocument(wrkPrjFile).removeObject(wrkShapeTarget)
	App.getDocument(wrkPrjFile).recompute()
	### End command Std_Delete

def rtnSelection(startNdx, endNdx):
	Gui.Selection.clearSelection()
	wrkShapeLabel = "wrkShapeLabel:: initialized"
	if startNdx == 0:  #  if first item in list use the default Shape label
		Gui.Selection.addSelection(wrkPrjFile,wrkShapeObj)
		App.Console.PrintMessage('rtnSelection:: startNdx 0')
		App.Console.PrintMessage('\n')
	else:  #if starting at some other place in the list reset Shape??? naming
		stri = getStri(startNdx)
		wrkShapeLabel = wrkShapeObj+stri
		Gui.Selection.addSelection(wrkPrjFile,wrkShapeLabel)
		# dev 
		App.Console.PrintMessage('startNdx > 0')
		# dev 
		App.Console.PrintMessage('\n')

	 #dev 
	App.Console.PrintMessage(wrkShapeLabel)
	 #dev 
	App.Console.PrintMessage('\n')
	#startNdx += 1	# assumes the first item is skipable but needed in selection
	""" exclude not needed used to exclude specific Shapes from selection
	while startNdx < endNdx + 1:	# first item named Shape 2nd Shape001
		wrkShapeLabel = 'Nope'
		#dev 
		App.Console.PrintMessage(startNdx)
		#dev 
		App.Console.PrintMessage('\n')
		stri = getStri(startNdx)
		wrkShapeLabel = wrkShapeObj+stri 
		Gui.Selection.addSelection(wrkPrjFile,wrkShapeLabel)
		if (wrkShapeLabel != 'Shape004'): # or (wrkShapeLabel != 'Shape009'):   #Assumes droppabble polygons non-tube paths
			App.Console.PrintMessage(wrkShapeLabel)
			App.Console.PrintMessage('\n')
		startNdx += 1
	"""
	return 	Gui.Selection.getSelection()	#selectItems = 



# Create the basic FC assy  project

# create a new 000_995_trash FC project


### STEP 2: Create Shape...Shape03 using uncomment below then Comment-out

"""
#$$$ Begin Op
App.Console.PrintMessage("Comment/UnComment as Needed\n")
#comment-out for dev 
#working 250102 lu
coneBraceFront()
#$$$ end Op
"""


### STEP 3: create FusedFrntShockAbsorberBrace by 
###			1> Uncommenting for veiwable between "#$$$ Begin Op" 
###				to "#$$$ End Op" for STEP 3:
###			2> Not USED::::Uncomment removeShape() in two places to delete Shape 4 and Shape9 
###			3> Run Macro again
###			4> Verifiy results
###				4.1> Shape..Shape003 selected (highlighted)
###				4.2>	 New Object: Label shown in Model Tree: FusedFrntBow_Chassis_
###				Note: All content below this STEP should be no-op or information print of 
###				message:  'End of Active Development'
###			5> Comment-out this step and move to STEP 4.
###				Note: Insure the two removeShap() entries are commented-out 



#$$$ Begin Op
#Prepare to fuse Cones and Rods of the  sections of Front Brace
# Once the bow "tubes" for the front chassis have been create 
#	fuse them into a Part called: FusedFrntShockAbsorberBrace

App.Console.PrintMessage("Comment/UnComment as Needed\n")
App.Console.PrintMessage("Select shapes in the Front Chassis Bow section\n")
#wrkShapeTarget= 'Shape004'    #front chassis bow polygon
#comment-out for dev removeShape(wrkShapeTarget)
#wrkShapeTarget= 'Shape009'    #front chassis aft polygon
#comment-out for dev removeShape(wrkShapeTarget)

#post removal of unwanted Labeled objects like polygon used for development
startNdx = 0		# start index  First Labeled item/tube/shape of chassis
endNdx   = 4		# total number of usable shapes last Labeled item/tube/shape of chassis	 

selectItems = rtnSelection(startNdx, endNdx)
newShape = selectItems[0].Shape
App.Console.PrintMessage(selectItems[0].Shape)
App.Console.PrintMessage('\n')

i = 1  # skip first selected shape "as Shape"
while i < endNdx:   # no longer worry about Shape 4
	newShape = newShape.fuse(selectItems[i].Shape)
	App.Console.PrintMessage(selectItems[i].Shape)
	App.Console.PrintMessage('while\n')
	i += 1
newObject = App.ActiveDocument.addObject("Part::Feature","FusedFrntShockAbsorberBrace\n")
newObject.Shape = newShape
App.ActiveDocument.recompute()
#$$$ End op
"""



### STEP 4: create Front Chassis Aft Section by 
###			1> Uncommenting for veiwable content between "#$$$ Begin Op" 
###				to "#$$$ End Op" for STEP 3:
###			2> Run Macro again
###			3> Verifiy results
###				3.1> Shape10..Shape013 selected (highlighted)
###				3.2>	 New Object: Label shown in Model Tree: FusedFrntAft_Chassis_
###			Note: All content below this STEP should be no-op or information print of 
###			message:  'End of Active Development'
"""


# Once the front shock absorber brace create 
#	fuse them into a Part called: FusedFrntShockAbsorberBrace


"""
### Begin Op
startNdx = 0		# First Labeled item/tube/shape of chassis
endNdx   = 3		# Last Labeled item/tube/shape of chassis	 
selectItems = rtnSelection(startNdx, endNdx)
newShape = selectItems[0].Shape  # new set of items 0-4
App.Console.PrintMessage(selectItems[0].Shape)
App.Console.PrintMessage('\n')
i = 1 # skip first selected shape
while i < 4:   # no longer worry about Shape 4
	newShape = newShape.fuse(selectItems[i].Shape)
	App.Console.PrintMessage(selectItems[i].Shape)
	App.Console.PrintMessage('\n')
	i += 1
newObject = App.ActiveDocument.addObject("Part::Feature","FusedFrntShockAbsorberBrace\n")
newObject.Shape = newShape
App.ActiveDocument.recompute()
### End Op
"""



App.Console.PrintMessage('End of Active Development') 
App.Console.PrintMessage('\n')
