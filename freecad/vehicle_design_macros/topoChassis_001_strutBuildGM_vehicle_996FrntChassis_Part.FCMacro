# -*- coding: utf-8 -*-
#***************************************************************************
#*                                                                               *
#*   Copyright (c) 1989- 2025 Abbott Analytical Products   <http://abbottanp.com/>*
#*                                                                               *
#* This program parameterically builds a chassis entity in exo cage in roll-out 
#*     ready state (less defined steering and suspension system) to use for 
#*     prototyping the invisioned Abiriba_RG  GM EV vehicle 
#*     detailed at: https://abbottanp.com/artifacts/gm_vehicle_WB/index.html.
#*Helpful Sites:
#*  Topographical scripting https://wiki.freecad.org/Topological_data_scripting
#*	Fuse/Union of Selected components
#*	  https://forum.freecad.org/viewtopic.php?t=4137 Re: Fuse multiple parts in 
#*		python macro fails Post by wmayer » Mon Jun 10, 2013 with AAP adjustments
#*	Part Rotation:  Re: how to rotate an object (placement) by yorik 02/06/2012  
#*		https://forum.freecad.org/viewtopic.php?style=5&t=2213
#*		Alternately used LES_Tower style rotation used in topoChassisFrame.py line 204
#*		as seen Ln 204 	#circle.rotate(App.Vector(0, 0, 0),App.Vector(0, 0, 1), 90)
#*		and modified for FrontChassis rotate of 7.5 degrees about X-axis not Z-Axis
#*
#* Change History
#* 250123_lu Results perfect through testing of the frontChassisSection()
#			Test for the topoChassisToolbox usage of SF in the seting of lenght
#			diameter, and radius.

#* 250121_lu Successfully built CHassis Front Frame assembly using 
#*				aap_lib.topoChassisToolbox.frontChassisSection() 
#*				for 000_988_spike_aapLib_test.FCStd
#* 250119_lu testing the introduciton of topoCHASSISToolbox.py and the aap_lib module
#* 250103_lu run upon update of topoChassisFrame.py module 
"""
python console to reload a *.py module called by macro
import topoChassisFrame 
from importlib import reload
reload (topoChassisFrame)

"""
#* 250110_lu Tested as is creating proper 000_988_test4spike_assembleStruts4FrntChassis
#*				Rename as original macro and original 000_998_*.FCMacro
#* 250108_lu	Incorporate aap_lib finctions
#* 250104_lu Resolved *.py issue __init()__ return value.  Recipe seemed lost
#*			Removed double Part.show.  No longer need to remove polygon 4 and 9
#* 241020_lu rename and reorganize to conform to numering/naming where used style
#*				and strut-Part to subassy to assy maturity of design.
#* 241015_lu drop A2Plus usage from this macro and generate separte mainAssemble macro.
#* 241013_lu	add section Step 5 to A2Plus assemble Front Chassis using Bow and Aft struts
#*					as a single part/project and then rotate 7.5 degrees
#*				retrun to solve rotate drop of shape strut Shape001 transfor to non-strut shape
#*					Try the clone and rotate.  Use part of this flow until fused Bow Front Chassis fused
#*					and Aft Front Chassis sued.  The use A2Plus to import Front Chassis project as a Part
#*					then rotate.
#* 240923_lu	work resolve Shape004 and Shape009 issue from frontChassisSection().
#* 240921_lu	topoChassis_mainBuildGM_vehicle_001_FrntChassis.FCMacro working almost
#*				perfectly.  Shape001 chassisleg2 spins to a non-tube bow section 
#*				when fused with aft section.  Workaround proposed for cloning
#*				the Shape001 and fusing/union at clone level. lter.
#*
#*** Things That Go Bump In THe Night:
#***		1> Shape001 strut splits from FusedFrntBow_Chassis solid when fused with 
#***			FusedFrntAft_Chassis.  Trying the Part Design Boolean Union/Fuse produced
#***			anomaly.  Workaround: create a copy of Shape001 and clone it.  Then fuse/union
#***			it with the correcponding FusedFront_Chassis.  Untested as of 240921.


#uncomment for usage:
from topoChassisFrame import frontChassisSection  #, rearChassisSection
#uncomment for usage:
#from topoChassisCabin import cabinChassisSection
import FreeCAD as App
import aap_lib
#* 250110_lu Not ready for prime time from aap_lib import topoChassisToolbox


__title__="Fuse the Front Chassis Components into A Part/Clone With A Macro"
__author__ = "Lucca Uzzo"
__url__ = "http://abbottanp.com"


# begin abstract from aapLib_fire1.FCMacro
from aap_lib import aapfunctions, topoChassisToolbox

chassisTool_Error = 0
chassisListVar_Error = 0
chassisShapeOpn_Error = 0

try:
	wrktool = topoChassisToolbox.chassisTool()
except Exception:
	print("chassisTool issue.  wrktool can not be defined")
	chassisTool_Error = 9
try:
    wrkdata = topoChassisToolbox.chassisListVar()
except Exception:
    print("chassisListVar issue.  wrkdata can not be defined")
    chassisListVar_Error = 9
try:
    wrkShape= topoChassisToolbox.chassisShapeOpn()
except Exception:
    print("chassisShapeOpn issue.  wrkdata can not be defined")
    chassisShapeOpn_Error = 9



#testing for trigger
### STEP 1: create, save, close, then invoke/activate new project file
#wrkPrjFile = "_00_988_spike_assembleFrntChassis"
#* 241124_lu for testing only
#wrkPrjFile = "_0_001_test"
#wrkPrjFile = "_00_0188_spike_tryassembleFrntChassis"
## testing the aap_lib library 
#             000_988_spike_aapLib-test.FCStd
wrkPrjFile = "_00_988_998_spike_aapLib_test_PIPE3_5_RADIUS"  
#wrkPrjFile = "_00_988_test4spike_assembleStruts4FrntChassis"
wrkShapeObj   = 'Shape'      #Let FreeCAD do the naminging work during building
# dev wrkPrjFile = "_03_963_chassis_topoScripting_cabin_mainBuild"   # copy Project file "label" from property and replace first character with underscore


App.setActiveDocument(wrkPrjFile)
App.ActiveDocument=App.getDocument(wrkPrjFile)
Gui.ActiveDocument=Gui.getDocument(wrkPrjFile)

#* Not ready for prime time
#*aapwrk 		= topoChassisToolbox.chassisTool()
#*aapshape		= topoChassisToolbox.chassisShapeOpn(wrkPrjFile, wrkShapeObj)


def getStri(fixNdx):
		if fixNdx <= 9 :
			stri = '00' + str(fixNdx)
		elif fixNdx <= 99:
			stri = '0' + str(fixNdx)
		elif fixNdx <= 999:
			stri = str(fixNdx)
		return stri

"""
These three function need to go into aap_lib.chassisShapeOpn
250119_lu chassisShapeOpn dev and test will be done at a later time.
The first priority is the chassis and cabin development
"""

def removeShape(wrkShapeTarget):
	### Begin command Std_Delete
	App.getDocument(wrkPrjFile).removeObject(wrkShapeTarget)
	App.getDocument(wrkPrjFile).recompute()
	### End command Std_Delete

def rtnSelection(inNdx, endNdx):
	Gui.Selection.clearSelection()
	if inNdx == 0:  #  if first item in list use the default Shape label
		Gui.Selection.addSelection(wrkPrjFile,wrkShapeObj)
		App.Console.PrintMessage('startNdx 0   \n')
		startNdx = 1	# assumes the first item is skipable but needed in selection
	else:  #if starting at some other place in the list reset Shape??? naming
		stri = getStri(inNdx)
		wrkShapeLabel = wrkShapeObj+stri
		Gui.Selection.addSelection(wrkPrjFile,wrkShapeLabel)
		# dev App.Console.PrintMessage('startNdx > 0')
		# dev App.Console.PrintMessage('\n')
	# dev 
		App.Console.PrintMessage(wrkShapeLabel+ '\n')
	while inNdx < endNdx + 1:	# first item named Shape 2nd Shape001
		wrkShapeLabel = 'Nope'
		#dev 
		App.Console.PrintMessage('index: ' + str(inNdx) + '\n')
		stri = getStri(inNdx)
		wrkShapeLabel = wrkShapeObj+stri 
		App.Console.PrintMessage("Attempt Shape add: " + wrkShapeLabel + '\n')
		Gui.Selection.addSelection(wrkPrjFile,wrkShapeLabel)
		App.Console.PrintMessage("Shape added: " + wrkShapeLabel + '\n')
		inNdx += 1
		
	# dev App.Console.PrintMessage('\n')
	#why ??? startNdx += 1	# assumes the first item is skipable but needed in selection
	return 	Gui.Selection.getSelection()	#selectItems = 



# Create the basic front suspension assy   

# create a new 000_995_trash FC project   ????***.FCStd


### STEP 2: Create Shape...Shape013 using uncomment below then Comment-out

"""
App.Console.PrintMessage("Comment/UnComment as Needed\n")
#comment-out for dev 
App.Console.PrintMessage('Calling: frontChassisSection()\n') 
"""
frontChassisSection()

"""
"""

### STEP 3: create Front Chassis Bow Section by 
###			1> Uncommenting for veiwable between "#$$$ Begin Op" 
###				to "#$$$ End Op" for STEP 3:
###			2> Uncomment removeShape() in two places to delete Shape 4 and Shape9 
###			3> Run Macro again
###			4> Verifiy results
###				4.1> Shape..Shape008 selected (highlighted)
###				4.2>	 New Object: Label shown in Model Tree: FusedFrntBow_Chassis_
###				Note: All content below this STEP should be no-op or information print of 
###				message:  'End of Active Development'
###			5> Comment-out this step and move to STEP 4.
###				Note: Insure the two removeShap() entries are commented-out 



#$$$ Begin Op
#Prepare to fuse bow and aft sections of Front Chassis
# Once the bow "tubes" for the front chassis have been create 
#	fuse them into a Part called: FusedFrntBow_Chassis

"""
#Programically removed the extanerous polygon shapes at *.py level
#post removal of unwanted Labeled objects like polygon used for development
zeroNdx  = 0		# Add First Labeled item/tube/shape of chassis to selction
startNdx = 1		#
endNdx   = 7  	# Last Labeled item/tube/shape of chassis	 

#selectItems = aapshape.rtnSelection(zeroNdx, endNdx)
selectItems = rtnSelection(zeroNdx, endNdx)
newShape = selectItems[zeroNdx].Shape
App.Console.PrintMessage(selectItems[zeroNdx].Shape)
App.Console.PrintMessage('\n')

i = startNdx  # start adding selected itmes but skip first selected shape
while i < endNdx:   # no longer worry about Shape 4
	App.Console.PrintMessage('index sought: ' + str(i) + '\n')
	newShape = newShape.fuse(selectItems[i].Shape)
	App.Console.PrintMessage(selectItems[i].Shape)
	App.Console.PrintMessage('\n')
	i += 1
newObject = App.ActiveDocument.addObject("Part::Feature","FusedFrntBow_Chassis\n")
newObject.Shape = newShape
App.ActiveDocument.recompute()
#$$$ End op
"""



### STEP 4: create Front Chassis Aft Section by 
###			1> Uncommenting for veiwable content between "#$$$ Begin Op" 
###				to "#$$$ End Op" for STEP 3:
###			2> Run Macro again
###			3> Verifiy results
###				3.1> Shape10..Shape013 selected (highlighted)
###				3.2>	 New Object: Label shown in Model Tree: FusedFrntAft_Chassis_
###			Note: All content below this STEP should be no-op or information print of 
###			message:  'End of Active Development'

"""

# Once the aft "tubes" for the front chassis have been create 
#	fuse them into a Part called: FusedFrntAft_Chassis

"""
"""
### Begin Op
startNdx = 8		# First Labeled item/tube/shape of chassis
endNdx   = 11	# Last Labeled item/tube/shape of chassis	 
#^ selectItems = aapshape.rtnSelection(startNdx, endNdx)
selectItems = rtnSelection(startNdx, endNdx)
newShape = selectItems[0].Shape  # new set of items 0-4
App.Console.PrintMessage(selectItems[0].Shape)
App.Console.PrintMessage('\n')
i = 1 # skip first selected shape
while i < 4:   # no longer worry about Shape 4
	App.Console.PrintMessage('index sought: ' + str(i) + '\n')
	newShape = newShape.fuse(selectItems[i].Shape)
	App.Console.PrintMessage(selectItems[i].Shape)
	App.Console.PrintMessage('\n')
	i += 1
newObject = App.ActiveDocument.addObject("Part::Feature","FusedFrntAft_Chassis\n")
newObject.Shape = newShape
App.ActiveDocument.recompute()
### End Op
"""




App.Console.PrintMessage('End of Active Development') 
App.Console.PrintMessage('\n')
