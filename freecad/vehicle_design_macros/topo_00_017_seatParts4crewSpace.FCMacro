# -*- coding: utf-8 -*-
#***************************************************************************
#*                                                                               *
#*   Copyright (c) 1989- 2025 Abbott Analytical Products   <http://abbottanp.com/>*
#*                                                                               *
#* This program parameterically builds the seat components for the crew space
#*     supporing the chassis assembly in roll-out ready state (less defined 
#*     steering system) to use for prototyping the invisioned Abiriba_RG  GM 
#*     EV vehicle detailed at: 
#*     https://abbottanp.com/artifacts/gm_vehicle_WB/index.html.
#* Helpful references:
#*  Topographical scripting https://wiki.freecad.org/Topological_data_scripting
"""
250126_lu Inital inputs
"""
import pdb, math              # python debugger  see python_gdb.sh for shell script
import FreeCAD as App
import Part, math,Draft
import numpy as np
from FreeCAD import Base
import aap_lib

__title__="Fuse the Front Chassis Components into A Part/Clone With A Macro"
__author__ = "Lucca Uzzo"
__url__ = "http://abbottanp.com"


# begin abstract from aapLib_fire1.FCMacro
from aap_lib import aapfunctions, topoChassisToolbox

chassisTool_Error = 0
chassisListVar_Error = 0
chassisShapeOpn_Error = 0

try:
	wrktool = topoChassisToolbox.chassisTool()
except Exception:
	print("chassisTool issue.  wrktool can not be defined")
	chassisTool_Error = 9
try:
    wrkdata = topoChassisToolbox.chassisListVar()
except Exception:
    print("chassisListVar issue.  wrkdata can not be defined")
    chassisListVar_Error = 9
try:
    wrkShape= topoChassisToolbox.chassisShapeOpn()
except Exception:
    print("chassisShapeOpn issue.  wrkdata can not be defined")
    chassisShapeOpn_Error = 9

wrkPrjFile = "_00_769_995_seatParts_aasy"  
wrkShapeObj   = 'Shape'      #Let FreeCAD do the naminging work during building

App.setActiveDocument(wrkPrjFile)
App.ActiveDocument=App.getDocument(wrkPrjFile)
Gui.ActiveDocument=Gui.getDocument(wrkPrjFile)


SF = wrkdata.get_SF()


FORCE_SEATBOTTOM = 40
FORCE_SEATBACK	   = 41
FORCE_SEATBRACKET1= 42
FORCE_SEATBRACKET2= 43

"""

by eyeball of bottom seat sketch
inches
0,0,0
0,0,3.4362
-1.4707ft,0,3,4362
-1.4707ft,0,0
-1.3664ft,0,1.1131
-1.3457ft,0.1.9362
-1.5,0,1.9362
-1.2143,0,1.0922
0,0,0
"""
#mm
pts40_Opn = [  # ndx ?* where * indicates start for shape
App.Vector(0,0,0),     #ndx 0 Sketch.Vertex1	 Shape0.1
App.Vector(0,0,-87.27948),    #ndx 1 Sketch.Vertex2	 Shape0.2
App.Vector(448.26936, 0, -87.27948),    #ndx 2 Sketch.Vertex2	 Shape1.1
App.Vector(448.26936, 0, 0),    #ndx 3 Sketch.Vertex3	 Shape1.2
App.Vector(416.47872, 0, -49.17948),
App.Vector(38.1, 0, -49.17948),    #ndx 6 Sketch.Vertex4	 Shape3.1
App.Vector(0, 0, 0),
App.Vector(0, 10, 0)]   #extrude in inches along  Y

pts41_Opn = [  # ndx ?* where * indicates start for shape
App.Vector(0,0,0),     #ndx 0 Sketch.Vertex1	 Shape0.1
App.Vector(0,0,-87.27948),    #ndx 1 Sketch.Vertex2	 Shape0.2
App.Vector(448.26936, 0, -87.27948),    #ndx 2 Sketch.Vertex2	 Shape1.1
App.Vector(448.26936, 0, 0),    #ndx 3 Sketch.Vertex3	 Shape1.2
App.Vector(416.47872, 0, -49.17948),
App.Vector(38.1, 0, -49.17948),    #ndx 6 Sketch.Vertex4	 Shape3.1
App.Vector(0, 0, 0),
App.Vector(0, 24, 0)]   #extrude in inches along  Y

pts42_Opn =[                             # ndx ?* where * indicates start for shape
App.Vector(0.0,71.2845,62.1614),      #Vertex1',
App.Vector(0.00,61.805,62.2487),        # Edge1',
App.Vector(0.00,29.2276,51.2344),
App.Vector(0.00,5.28459,22.4609),
App.Vector(0.0,0,0),	                    # Vertex2'
App.Vector(0.0,65.9384,-3.66183),     # Vertex3',
App.Vector(0.0,71.2845,62.1614)]       #Vertex1',


"""
original
App.Vector(0,0,0),     #ndx 0 Sketch.Vertex1	 Shape0.1
App.Vector(0.014,71.2845,62.1614),			#Vertex1
App.Vector(0.014,0,0),							#Vertex2
App.Vector(0.014,65.9384,-3.66183),			#Vertex3
App.Vector(0.014,59.2424,0),					#Vertex5
App.Vector(0, 0, 0),
App.Vector(wrktool.toMM(.5),0,0)		#Extrude in X axis direction
 ]
"""

class OpnMgr(object):   #no longer child of ChassisLeg
#class ChassisArch(object):   #no longer child of ChassisLeg	# def setupArchHndlr(pts, subChassisID):
	def __init__(self, pts, subChassisID):  #xa, ya, za, xb, yb, zb, subChassisID):
		rtnMessage = "Nobody Home\n"
		if subChassisID == FORCE_SEATBOTTOM:
			self.fabComponent(pts40_Opn, subChassisID)
		if subChassisID == FORCE_SEATBACK:
			self.fabComponent(pts41_Opn, subChassisID)
		if subChassisID == FORCE_SEATBRACKET1:
			self.fabComponent(pts42_Opn, subChassisID)
		if subChassisID == FORCE_SEATBRACKET2:  
			#use same shape array but displace width of seat
			self.fabComponent(pts42_Opn, subChassisID)
		rtnMessage = "\n__init__ done\n"
		#App.getDocument(wrkPrjFile).recompute()
		App.Console.PrintMessage(rtnMessage)

	def fabComponent(self,pts4Wrk, subChassisID):
		#See Example3 of spike 005_999_spline_pipe.FCStd 
		#	and Macro 005_999_buildsplinePipe.FCMacro
		np_Arr   = np.array(pts4Wrk)  #vLoc
		#load from 0: loopNdx = 0  
		ShapePairNdx = 0 #ndx for first Vertex1 of four vertex shape
		ShapeQty = 7 #2 #7 #number of shapes beginning with 0 
		for ShapePairNdx in range(ShapeQty):
			zAngle = 90 #270
			if ShapePairNdx == 0:
				startArrayNdx = 0	# look for arry index pointer to first vertex
				appVector1   = self.buildArr(np_Arr[startArrayNdx], startArrayNdx)
			if ShapePairNdx == 1:
				startArrayNdx = 1 # was1	# Vertex2 to Vertex3
				appVector2   = self.buildArr(np_Arr[startArrayNdx], startArrayNdx)
			if ShapePairNdx == 2:
				startArrayNdx = 2	#Vertex 3 to Vertex 4
				appVector3 = self.buildArr(np_Arr[startArrayNdx], startArrayNdx)
			if ShapePairNdx == 3:
				startArrayNdx = 3 #Vertex 5 to Vertex
				appVector4   = self.buildArr(np_Arr[startArrayNdx], startArrayNdx)
			if ShapePairNdx == 4:
				startArrayNdx = 4 #Vertex 5 to Vertex
				appVector5   = self.buildArr(np_Arr[startArrayNdx], startArrayNdx)
			if ShapePairNdx == 5:
				startArrayNdx = 5 #Vertex 5 to Vertex
				appVector6   = self.buildArr(np_Arr[startArrayNdx], startArrayNdx)
			if ShapePairNdx == 6:
				startArrayNdx = 6 #Vertex 5 to Vertex
				appVector7   = self.buildArr(np_Arr[startArrayNdx], startArrayNdx)
			if ShapePairNdx == 7:
				startArrayNdx = 7 #Vertex 5 to Vertex
				appVector8   = self.buildArr(np_Arr[startArrayNdx], startArrayNdx)
		seatWire = Part.makePolygon([appVector1, appVector2, appVector3, appVector4, appVector5, appVector6, appVector7])
		if subChassisID == 40:
			padLen = wrktool.toMM(10)  #ten inches seat 
			self._tube = seatWire.extrude(App.Vector(0, padLen, 0))
			movLenY = wrktool.toMM(-8)  #eighteen inches height
			movLenZ = wrktool.toMM(2)
			self._tube.translate(App.Vector(0, movLenY, movLenZ))
		if subChassisID == 41:
			padLen = wrktool.toMM(20)  #eighteen inches height
			self._tube = seatWire.extrude(App.Vector(0, padLen, 0))
			self._tube.rotate(App.Vector(0, 0, 0),App.Vector(1, 0, 0), 75)
		if subChassisID == 42:
			padLen = wrktool.toMM(.5) #bracket thickness
			self._tube = seatWire.extrude(App.Vector(padLen,0,0))
			movLenX = wrktool.toMM(-.25)
			self._tube.translate(App.Vector(movLenX, 0, 0))
		if subChassisID == 43:
			padLen = wrktool.toMM(.5) #bracket thickness
			self._tube = seatWire.extrude(App.Vector(padLen,0,0))
			movLenX = wrktool.toMM(1.4707 *12) -wrktool.toMM(.25)
			self._tube.translate(App.Vector(movLenX, 0, 0))
		seatSolid = Part.makeSolid(self._tube)
		Part.show(seatSolid)
		#self._tube = super().__init__(xa,ya, za, xbe, ybe, zbe, CHASSIS_CABIN_STARBOARD)
		#use with while loopNdx -= 1

	def buildArr(self, np_Arr, ndx):
		pntNdx     = ndx
		wrkArrNa   = np_Arr
		x1         = wrkArrNa[0]		#yields the x-axis vector component of bow 2d cross-section	 
		y1         = wrkArrNa[1]		#yields the sections length from aft to bow
		z1         = wrkArrNa[2]	
		newAppVector = App.Vector(x1,y1,z1)
		App.Console.PrintMessage("wrkArrN:: x1, y1, z1\n")
		App.Console.PrintMessage(wrkArrNa)
		App.Console.PrintMessage("\n")
		return newAppVector

	def fabHardwareBracket(self,pts4Wrk, subChassisID):
		np_Arr   = np.array(pts4Wrk)  #vLoc
		ShapePairNdx = 0 #ndx for first Vertex1 of four vertex shape
		ShapeQty = 7 #2 #7 #number of shapes beginning with 0 
		for ShapePairNdx in range(ShapeQty):
			zAngle = 90 #270
			if ShapePairNdx == 0:
				startArrayNdx = 0	# look for arry index pointer to first vertex
				appVector1   = self.buildArr(np_Arr[startArrayNdx], startArrayNdx)
			if ShapePairNdx == 1:
				startArrayNdx = 1 # was1	# Vertex2 to Vertex3
				appVector2   = self.buildArr(np_Arr[startArrayNdx], startArrayNdx)
			if ShapePairNdx == 2:
				startArrayNdx = 2	#Vertex 3 to Vertex 4
				appVector3 = self.buildArr(np_Arr[startArrayNdx], startArrayNdx)
			if ShapePairNdx == 3:
				startArrayNdx = 3 #Vertex 5 to Vertex
				appVector4   = self.buildArr(np_Arr[startArrayNdx], startArrayNdx)
			if ShapePairNdx == 4:
				startArrayNdx = 4 #Vertex 5 to Vertex
				appVector5   = self.buildArr(np_Arr[startArrayNdx], startArrayNdx)
			if ShapePairNdx == 5:
				startArrayNdx = 5 #Vertex 5 to Vertex
				appVector6   = self.buildArr(np_Arr[startArrayNdx], startArrayNdx)
			if ShapePairNdx == 6:
				startArrayNdx = 6 #Vertex 5 to Vertex
				appVector7   = self.buildArr(np_Arr[startArrayNdx], startArrayNdx)
			if ShapePairNdx == 7:
				startArrayNdx = 7 #Vertex 5 to Vertex
				appVector8   = self.buildArr(np_Arr[startArrayNdx], startArrayNdx)
		padLen = 0
		if subChassisID == 42:
			padLen = wrktool.toMM(.5) #bracket thickness
		hwObj = Part.makePolygon([appVector1, appVector2, appVector3, appVector4, appVector5, appVector6, appVector7])
		Part.show(hwObj)
		hwWire=Part.Wire(hwObj)
		ruptureDisk = Part.Face(hwWire)
		padBracket = ruptureDisk.extrude(App.Vector( padLen, 0,0))
		seatSolid = Part.makeSolid(padBracket)
		Part.show(seatSolid)
		pass

def hndlSeatBottom():
	aap40Assign = OpnMgr(pts40_Opn, FORCE_SEATBOTTOM)	

def hndlSeatBack():
	aap41Assign = OpnMgr(pts41_Opn, FORCE_SEATBACK)	

def hndlSeatBracket1():
	aap42Assign = OpnMgr(pts42_Opn, FORCE_SEATBRACKET1)	

def hndlSeatBracket2():
	#reuse pts42 but displace in x-direction seat width 1.4707 ft  448.26936mm
	aap42Assign = OpnMgr(pts42_Opn, FORCE_SEATBRACKET2)	


hndlSeatBottom()
hndlSeatBack()
hndlSeatBracket1()
hndlSeatBracket2()
